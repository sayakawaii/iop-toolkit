module nokia-sdan-l2-forwarding-forwarding-database-macaddress-hierarchy-meta-ref {
  yang-version 1.1;
  namespace "http://www.nokia.com/Fixed-Networks/BBA/yang/"
          + "nokia-sdan-l2-forwarding-forwarding-database-hierarchy-meta-ref";
  prefix nokia-sdan-l2-fwd-meta-ref;

  import bbf-l2-forwarding {
    prefix bbf-l2-fwd;
  }

  organization
    "Nokia";

  contact
    "Comments or questions about this Nokia YANG module should be
     directed to <mailto:isam.yang@nokia.com>.";

  description
    "This module contains a collection of YANG definitions for
     supporting Nokia specific requirements as applicable to its
     access network equipment.
     Specifically this module contains a collection of YANG
     definitions for actions to be executed on forwarding databases.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2026-01-15 {
    description
      "Changed yang name from hiearchy to hierarchy.";
    reference
      "Nokia specific";
  }

  revision 2025-11-28 {
    description
      "Initial revision.
       * Approval Date:    see revision date above.
       * Publication Date: yyyy-mm-dd.";
    reference
      "Nokia specific";
  }

   augment "/bbf-l2-fwd:forwarding-state"
        + "/bbf-l2-fwd:forwarding-databases"
        + "/bbf-l2-fwd:forwarding-database"
        + "/bbf-l2-fwd:mac-addresses"
        + "/bbf-l2-fwd:mac-address"
        + "/bbf-l2-fwd:learned-on"
        + "/bbf-l2-fwd:forwarder-port" {
    description
      "Augment mac-address with the hierarchy meta info data.";

    leaf hierarchy-meta-info-reference {
      type string;
      description
        "Hierarchy meta info data.";
    }
  }

}
