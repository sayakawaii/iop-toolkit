module nokia-sdan-hardware-pm-threshold-profiles-mounted {
  yang-version 1.1;
  namespace "http://www.nokia.com/Fixed-Networks/BBA/yang/"
          + "nokia-sdan-hardware-pm-threshold-profiles-mounted";
  prefix nokia-hw-pm-threshold-prof-mounted;

  import bbf-yang-types {
    prefix bbf-yang;
  }
  import nokia-yang-types-mounted {
    prefix nok-typ-mounted;
  }
  import nokia-hardware-profiles-mounted {
    prefix nokia-hw-prof-mounted;
  }
  import bbf-fiber-onu-emulated-mount {
    prefix onu;
  }

  organization
    "Nokia";
  contact
    "Comments or questions about this Nokia YANG module should be
     directed to <mailto:isam.yang@nokia.com>.";
  description
    "This module contains a collection of YANG definitions for
     supporting Nokia specific requirements as applicable to its
     access network equipment.

     Specifically, this module augments the hardware model with
     data that supports configuring thresholding values for
     performance data associated with hardware components.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2022-05-16 {
    description
      "Implementation of threshold profiles to assiciate with
       performance monitoring data.";
    reference
      "Nokia specific";
  }

  augment "/onu:onus/onu:onu/onu:root/nokia-hw-prof-mounted:tca-profiles" {
    description "augment tca profiles";
    container pm-profiles {
      description
        "TCA profiles related performance monitoring";
      list system-load-profile {
        key "name";
        description
          "TCA profile to configure CPU load thresholding values";
        leaf name {
          type nok-typ-mounted:nokia-string-ascii64;
          description
            "Indicates name of the profile that can be applied to thresholding of CPU
             performace monitoring data.";
        }
        leaf threshold {
          type bbf-yang:percent;
          units "percent";
          description
            "Threshold value for the average calculated CPU load over the previous fifteen
             minutes. When average calculated CPU load crosses this threshold limit, a TCA is raised.
             Once raised, the alarm will be held at least until the end of the interval in
             which it was raised. It will be cleared once the CPU load falls below the threshold
             level in one of the next intervals.";
        }
      }
      list memory-usage-profile {
        key "name";
        description
          "TCA profile to configure memory usage parameters";
        leaf name {
          type nok-typ-mounted:nokia-string-ascii64;
          description
            "Indicates name of the profile that can be applied to thresholding of memory usage
             performace monitoring data.";
        }
        leaf threshold {
          type bbf-yang:percent;
          units "percent";
          description
            "Threshold value for the amount of memory that is currently in use.
             When memory usage crosses this threshold limit, a TCA is raised. Once raised the alarm
             will be held at least until the end of the interval in which it was raised. It
             will be cleared once the used memory falls below the threshold level in one of
             the next intervals.";
        }
      }
    }
  }
}
