submodule bbf-media-statistics-mounted {
  yang-version 1.1;
  belongs-to bbf-sip-voip-mounted  {
    prefix bbf-sip-voip-mounted;
  }

  import bbf-yang-types {
    prefix bbf-yang;
  }
 
 organization
    "Broadband Forum <https://www.broadband-forum.org>
     Common YANG Work Area";

 contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains a collection of YANG definitions for
     managing media forwarder.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

 revision 2020-03-06 {
    description
      "Initial revision.
       * Approval Date:    see revision date above.
       * Publication Date: 2020-03-06.";
    reference
      " ";
  }
  
  grouping media-statistics {
    container statistics {
	leaf sent-rtp-packets {
	  type bbf-yang:performance-counter32;
//	  config false;	  
	  description
	    "The total amount of RTP packets transmit.";
	}		
        leaf received-rtp-packets {
	  type bbf-yang:performance-counter32;
//	  config false;	  
	  description
	    "The total amount of RTP packets received.";
	}	
	leaf jitter-maximum {
	  type bbf-yang:performance-counter32;
//	  config false;	
	  description
	    "is a high-water mark that represents the maximum jitter
 	     identified during a measured interval, expressed in RTP 
	     timestamp units.";
	}	
	leaf buffer-underflows {
          type bbf-yang:performance-counter32;
//          config false;	  
          description
            "counts the number of times the reassembly buffer 
             underflows. In case of continuous underflow caused by a 
             loss of IP packets, a single buffer underflow should be
	     counted. If the interworking function is implemented with 
             multiple buffers, such as a packet level buffer and a bit 
	     level buffer, then underflow of either buffer increments 
             this counter.";
	}	
        leaf buffer-overflows {
          type bbf-yang:performance-counter32;
//          config false;	  
          description
	   "counts the number of times the reassembly buffer 
	    overflows. If the interworking function is implemented 
   	    with multiple buffers, such as a packet level buffer and
	    a bit level buffer, then overflow of either buffer 
	    increments this counter.";	
        }
    }
  }	
}
