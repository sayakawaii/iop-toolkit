module bbf-xpon-ploam-authentication {
  namespace "urn:bbf:yang:bbf-xpon-ploam-authentication";
  yang-version 1.1;
  prefix bbf-xpon-ploam-authentication;

  import ietf-interfaces {
    prefix if;
  }

  import bbf-xpon {
    prefix bbf-xpon;
  }

  organization
    "NOKIA Broadband Forum <https://www.broadband-forum.org>
     Fiber Access Networks Work Area";
  contact
    "Comments or questions about this Broadband Forum YANG module
     should be directed to <mailto:help@broadband-forum.org>.

     Editor:      Joey Boyd, ADTRAN

     Editor:      Samuel Chen, Broadcom

     Editor:      Robert Peschi, Nokia

     WA Director: Marta Seda, Calix

     WA Director: Lin Wei, Huawei";
  description
    "This module contains a collection of YANG definitions which
     in relation with ONU PLOAM authentication failure in the xPON
     YANG models.

     Copyright (c) 2018, //NOKIA Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385; see
     the TR itself for full legal notices.";

  revision 2019-02-25 {
    description
      "Initial revision.
       * Approval Date:    2019-02-25.
       * Publication Date: 2019-02-25.";
    reference
      "TR-385: ITU-T PON YANG Modules
               <https://www.broadband-forum.org/technical/download/
                        TR-385.pdf>";
  }

  identity ploam-authentication-failure-control {
    description
      "This identity is used to tell how the OLT must react
       when a discovered ONU fails all authentication
       possibilities following PLOAM messages exchange.";
  }

  identity keep-onu-ranged {
    base ploam-authentication-failure-control;
    description
      "This identity is used to denote that the OLT allows
       the ONU to reach O5 state and exchange OMCI messages.";
  }

  identity enable-silent-period {
    base ploam-authentication-failure-control;
    description
      "This identity is used to indicate that the OLT must
       send a '0x05-Deactivate_ONU-ID'PLOAM request to the
       ONU bringing it to state O1.";
    reference
      "ITU-T G.984.3 Section 9.2.1
       ITU-T G.987.3 Table 11.2
       ITU-T G.9807.3 Table C.11.2
       ITU-T G.989.3 Table 11.2";
  }

  augment '/if:interfaces/if:interface/bbf-xpon:channel-pair' {
    description
      "Complement the configuration of an xPON channel pair.";
    leaf onu-ploam-authentication-fail-control {
      type identityref {
        base ploam-authentication-failure-control;
      }
      default "keep-onu-ranged";
      description
        "Determines how the OLT must react when a discovered ONU
         fails all authentication possibilities after PLOAM
         messages exchange.";
    }
  }
}
