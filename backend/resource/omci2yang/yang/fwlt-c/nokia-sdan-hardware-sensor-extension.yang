module nokia-sdan-hardware-sensor-extension {

  yang-version 1.1;
  namespace "http://www.nokia.com/Fixed-Networks/BBA/yang/"
  + "nokia-sdan-hardware-sensor-extension";

  prefix nokia-sdan-hw-sens-ext;

  import iana-hardware {
    prefix ianahw;
  }

  import ietf-hardware {
    prefix hw;
  }

  organization
    "Nokia";

  contact
    "Comments or questions about this Nokia YANG module should be
     directed to <mailto:isam.yang@nokia.com>.";

  description
    "This module contains a collection of YANG definitions for
     supporting Nokia specific requirements as applicable to its
     access network equipment.

     Specifically, this module augments the hardware model with
     additional identifying operational data of a sensor component.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

     revision 2024-03-14 {
       description
         "Support Nokia specific sensor state data fields";
       reference
         "Nokia specific";
     }

     augment "/hw:hardware-state/hw:component" {
       when "derived-from-or-self (hw:class, 'ianahw:sensor')";
         description
         "Augment sensor hardware state with Nokia specific remote
          inventory data.";

     container temperature-sensor-thresholds {
       presence
        "Presence of this container indicates that component
         has temperature thresholds associated with it.";

     description
      "contains information on temperature thresholds";

      leaf threshold-high {
          type int32;
          units "degrees Celsius";
          config false;
          description
            "The threshold is involved in protecting the system against overheating. The threshold-high is the threshold to raise the overheat alarm.";
      }

      leaf threshold-high-clear {
          type int32;
          units "degrees Celsius";
          config false;
          description
            "The threshold is involved in indicating the overheating is eliminated. The threshold-high-clear is the threshold to clear the overheat alarm.";
      }

      leaf threshold-high-warning {
          type int32;
          units "degrees Celsius";
          config false;
          description
            "The threshold is involved in monitoring the system against overheating.";
      }

      leaf threshold-high-warning-clear {
          type int32;
          units "degrees Celsius";
          config false;
          description
            "The threshold indicates monitoring the system against overheating is eliminated.";
      }

      leaf threshold-low-warning {
          type int32;
          units "degrees Celsius";
          config false;
          description
            "The threshold is involved in monitoring the system against overcooling.";
      }

      leaf threshold-low-warning-clear {
          type int32;
          units "degrees Celsius";
          config false;
          description
            "The threshold indicates monitoring the system against overcooling is eliminated.";
      }

      leaf threshold-low {
          type int32;
          units "degrees Celsius";
          config false;
          description
            "The threshold is involved in protecting the system against overcooling. The threshold-low is the threshold to raise the overcool alarm.";
      }

      leaf threshold-low-clear {
          type int32;
          units "degrees Celsius";
          config false;
          description
            "The threshold is involved in indicating the overcooling is eliminated. The threshold-low-clear is the threshold to clear the overcool alarm.";
      }
    }
  }
}
