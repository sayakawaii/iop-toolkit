submodule bbf-xponani-ani-body-mounted {
  yang-version 1.1;
  belongs-to bbf-xponani-mounted  {
    prefix bbf-xponani-mounted;
  }

  import ietf-interfaces-mounted {
    prefix if-mounted;
  }
  import bbf-xpon-types {
    prefix bbf-xpon-types;
  }
  import bbf-fiber-onu-emulated-mount {
     prefix onu;
  }
  import bbf-yang-types {
    prefix bbf-yang;
  }  

  import bbf-xpon-if-type-mounted {
    prefix bbf-xponift-mounted;
  }
  
  include bbf-xponani-base-mounted;

  organization
    "Broadband Forum <https://www.broadband-forum.org>
     Fiber Access Networks Work Area";
  contact
    "Comments or questions about this Broadband Forum YANG module
     should be directed to <mailto:info@broadband-forum.org>.

     Editor:      Joey Boyd, ADTRAN

     Editor:      Igor Ternovsky, Broadcom

     Editor:      Robert Peschi, Nokia

     WA Director: Marta Seda, Calix

     WA Director: Samuel Chen, Broadcom";
  description
    "This submodule contains data related to the actual ONU devices.
     Each ONU device is 1:1 associated to its unique Access Network
     Interface (ANI).

     Copyright (c) 2018-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i2; see
     the TR itself for full legal notices.";

  revision 2020-10-13 {
    description
      "Issue 2.
       * Approval Date:    2020-10-13.
       * Publication Date: 2020-10-13.";
    reference
      "TR-385i2: ITU-T PON YANG Modules
               <https://www.broadband-forum.org/technical/download/
                        TR-385_Issue-2.pdf>";
  }
  revision 2019-02-25 {
    description
      "Initial revision.
       * Approval Date:    2019-02-25.
       * Publication Date: 2019-02-25.";
    reference
      "TR-385: ITU-T PON YANG Modules
               <https://www.broadband-forum.org/technical/download/
                        TR-385.pdf>";
  }

  feature configurable-ani-onu-id {
    description
      "Indicates support for configuration of the Optical Network Unit
       (ONU) ID associated with the Access Network Interface (ANI).";
  }

  feature configurable-ani-management-gem-port-id {
    description
      "Indicates support for configuration of the management
       G-PON Encapsulation Method (GEM) port.";
  }

  feature ani-onu-serial-number-reporting {
    description
      "Indicates that the Access Network Interface (ANI) holds the
       Optical Network Unit (ONU) serial number in its state data.";
  }

  feature ani-defects {
    description
      "Indicates support for reporting defects observed at the Access
       Network Interface (ANI).";
  }

  grouping ani-config-data {
    description
      "Configuration data intended for the Optical Network Unit (ONU)
       physical device. This data is brought to the ONU, when present,
       for instance via the Physical Layer Operations, Administrations
       and Maintenance (PLOAM) channel or using ONU Management and
       Control Interface (OMCI) on the Management G-PON Encapsulation
       Method (GEM) port.";
    leaf upstream-fec {
      type boolean;
      default "false";
      description
        "Enable/Disable use of Forward Error Correction (FEC) in the
         upstream direction for this specific Optical Network Unit
         (ONU).";
      reference
        "ITU-T G.984.3 clause 13.3.1.1
         ITU-T G.987.3 clause 10.2
         ITU-T G.9807.1 clause C.10.1.3.2.4
         ITU-T G.989.3 clause 10.1.3.2.4";
    }
    leaf management-gemport-aes-indicator {
      type boolean;
      default "false";
      description
        "Used to designate whether Advanced Encryption Standard
         (AES) should be enabled/disabled for the management G-PON
         Encapsulation Method (GEM) port of this Optical Network Unit
         (ONU).

         For G-PON, this applies in the downstream direction. For
         XG-PON, XGS-PON and NG-PON2, this applies to both the
         upstream and downstream directions.";
      reference
        "ITU-T G.984.3 section 12.1
         ITU-T G.987.3 section 15.5.1
         ITU-T G.9807.1 clause C.15.5.1
         ITU-T G.989.3 clause 15.5.1.";
    }
    leaf onu-id {
      if-feature "bbf-xponani-mounted:configurable-ani-onu-id";
      type bbf-xpon-types:onu-id;
      description
        "This is the TC layer ONU-ID identifier. When configured this
         is the value which the Optical Line Termination (OLT) must
         assign to the Optical Network Unit (ONU) during the ONU's
         activation using the Assign_ONU-ID Physical Layer Operations,
         Administrations and Maintenance (PLOAM) message. For G-PON
         the value should be in [0..253], for XG-PON it should be in
         [0..1022] and for XGS-PON and NG-PON2 it should be in
         [0..1020].";
      reference
        "ITU-T G.984.3 clause 5.5.2
         ITU-T G.987.3 clause 6.4.2
         ITU-T G.9807.1 clause C.6.1.5.6
         ITU-T G.989.3 clause 6.1.5.6";
    }
    leaf management-gemport-id {
      if-feature
        "bbf-xponani-mounted:configurable-ani-management-gem-port-id";
      type uint32;
      description
        "This leaf is only relevant to GPON ONUs; it is ignored for
         non-GPON ONUs. In contrast with other xPON technologies, in
         the case of G-PON, there is no requirement that the ITU-T TC
         ID of the management G-PON Encapsulation Method (GEM) port
         for the Optical Network Unit (ONU) is numerically equal to
         the ONU-ID. This leaf provides the capability to specify
         value for the management GEM port ID.

         If this leaf is not configured the management GEM port
         ID must be numerically equal to the ONU-ID.";
      reference
        "Refer to 'OMCC Port-ID' in
         ITU-T G.984.3 clause 5.5.5
         ITU-T G.987.3 clause 6.4.4
         ITU-T G.989.3, clause 6.1.5.8
         ITU-T G.9807.1 clause C.6.1.5.8";
    }
  }


  grouping onu-multicast-gemports-config-data {
    description
      "The config data of multicast GEM port(s), known by the ONU.
       Multicast GEM ports can be used for multicast or broadcast.";
    list multicast-gemport {
      key "name";
      leaf name {
        type bbf-yang:string-ascii64;
        description
      "The name of the multicast GEM port";
      }
 
    leaf mc-gemport-id {
      type uint32;
      mandatory true;
      description
          "ID of MC GEM port. When configured this is the value which 
           must actually be used between the OLT device and ONU
           device for this MC GEM port. For G-PON the value should
           be in [0..4095] and not conflicting with the 
           management-gemport-id, for XG-PON it should be
           in [1023..65534] and for XGS-PON and NG-PON2 it should 
           be in [1021..65534]. The ID of a MC GEM port may not conflict
           with the ID of a UNI cast GEM port";
      reference
        "ITU-T G.984.3 clause 5.5.5
         ITU-T G.987.3 clause 6.4.4
         ITU-T G.9807.1 clause C.6.1.5.8
         ITU-T G.989.3 clause 6.1.5.8";
    }

    leaf interface {
      type string;
      must
       "../../../../../if-mounted:interfaces/if-mounted:interface[if-mounted:name=current()]
        /if-mounted:type='bbf-xponift-mounted:onu-v-enet'" {
       error-message
         "Must reference a onu-v-enet.";
      }
      description
        "The vENET associated with this MC GEM port.";
    }

    leaf traffic-class {
      type uint8 {
        range "0..7";
    }
    description
      "Traffic class value.";
    }
    leaf is-broadcast {
     type boolean;
     default "false";
     description
       "If true, this multicast GEM port is used for broadcast traffic.";
    }
    description
      "List of multicast GEM ports.";
  }
 }  



  grouping ani-state-data {
    description
      "State data from the Optical Network Unit (ONU) physical device.
       This data is fetched from the ONU physical device, when
       present, for instance via the Physical Layer Operations,
       Administrations and Maintenance (PLOAM) channel or using ONU
       Management and Control Interface (OMCI) on the Management
       G-PON Encapsulation Method (GEM) port.";
    leaf onu-id {
      type bbf-xpon-types:onu-id;
      description
        "This is the TC layer ONU-ID identifier which the Optical Line
         Termination (OLT) has assigned to the Optical Network Unit
         (ONU) during the ONU's activation using the Assign_ONU-ID
         Physical Layer Operations, Administrations and Maintenance
         (PLOAM) message.";
      reference
        "ITU-T G.984.3 clause 5.5.2
         ITU-T G.987.3 clause 6.4.2
         ITU-T G.9807.1 clause C.6.1.5.6
         ITU-T G.989.3 clause 6.1.5.6";
    }
    leaf onu-serial-number {
      if-feature "bbf-xponani-mounted:ani-onu-serial-number-reporting";
      type bbf-xpon-types:onu-serial-number;
      mandatory true;
      description
        "The serial number of the Optical Network Unit (ONU).";
      reference
        "ITU-T G.984.3, clause 9.2.4.1
         ITU-T G.987.3, clause 11.3.3.2
         ITU-T G.9807.1, clauses C11.2.6.1, C11.2.6.2 and C11.3.4.1
         ITU-T G.989.3, clauses 11.2.6.1, 11.2.6.2 and 11.3.4.1.";
    }
    leaf channel-partition-id {
      type uint8;
      description
        "An index of the operator-specified channel subset in a
         NG-PON2 system. During operation, the Optical Network Units
         (ONUs) can be re-tuned between the channels within a channel
         partition, but not across the boundaries of the channel
         partition.";
    }
    leaf management-tcont-alloc-id {
      type uint32;
      description
        "The ITU-T Transmission Convergence (TC) Allocation Identifier
         (Alloc-ID) of the management Transmission Container (T-CONT)
         for the Optical Network Unit (ONU). It has the same numerical
         value as the ITU-T TC ONU-ID.";
      reference
        "Refer to 'Default Alloc-ID' in
         ITU-T G.987.3, clause 6.1.5.7
         ITU-T G.9807.1, clause C.6.1.5.7
         ITU-T G.987.3, clause 6.4.3
         ITU-T G.984.3, clause 5.5.3";
    }
    leaf management-gemport-id {
      type uint32;
      description
        "The ITU-T Transmission Convergence (TC) ID of the management
         G-PON Encapsulation Method (GEM) port for the Optical Network
         Unit (ONU). For NG-PON2, XGS-PON and XG-PON, it has the same
         numerical value as the ITU-T TC ONU-ID. For G-PON, its value
         is not necessarily numerically equal to the ONU-ID.";
      reference
        "Reefer to 'OMCC Port-ID' in
         ITU-T G.987.3, clause 6.1.5.8
         ITU-T G.9807.1, clause C.6.1.5.8
         ITU-T G.987.3, clause 6.4.4
         ITU-T G.984.3, clause 5.5.5";
    }
    /* leaf-list active-defects {
      if-feature "bbf-xponani-mounted:ani-defects";
      type identityref {
        base bbf-xpon-def:items-detected-at-onu;
      }
      description
        "Defects detected by Optical Network Unit (ONU) for which
         Access Network Interface (ANI) is configured. All applicable
         identities should be reported.";
      reference
        "ITU-T G.984.3 (01/2014) 11.1.2
         ITU-T G.987.3 (01/2014) 14.2.2
         ITU-T G.989.3 (2015)/Amd.2 (11/2018) Table 14-3
         ITU-T G.9807.1 (2016)/Amd.1 (10/2017) Table C.14.3 ";
    }*/
  }

  augment "/onu:onus/onu:onu/onu:root/if-mounted:interfaces/if-mounted:interface/bbf-xponani-mounted:ani" {
    description
      "Configuration of an xPON Access Network Interface (ANI), i.e.
       an Optical Network Unit (ONU) device.";
    uses ani-config-data;
    uses onu-multicast-gemports-config-data;
  }

  augment "/onu:onus/onu:onu/onu:root/if-mounted:interfaces-state/if-mounted:interface/bbf-xponani-mounted:ani" {
    description
      "State data of an xPON Access Network Interface (ANI), i.e.
       an Optical Network Unit (ONU) device.";
    uses ani-state-data;
  }
}
