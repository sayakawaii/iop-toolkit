module bbf-software-image-management-one-dot-one-mounted {
  yang-version 1.1;
  namespace "urn:bbf:yang:bbf-software-image-management-one-dot-one-mounted";
  prefix bbf-sim-mounted;
  
  include bbf-software-image-management-base-mounted;
  include bbf-software-image-management-common-body-mounted;
  include bbf-software-image-management-download-body-mounted;
  include bbf-software-image-management-revision-body-mounted;
  
  organization
    "Broadband Forum Common YANG Work Area";

  contact
    "Comments or questions about this Broadband Forum YANG module
     should be directed to <mailto:help@broadband-forum.org>.

     Editor:      TBD
     
     WA Director: William Lupton, Broadband Forum
                  <mailto:wlupton@broadband-forum.org>

     WA Director: Michael Shaffer
                  <mailto:michael.shaffer@nokia.com>";

  description
    "This module contains a collection of YANG definitions for 
     software image management on physical entities as defined 
     by ietf-entity.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms.

     Any moral rights which are necessary to exercise under the above
     license grant are also deemed granted under this license.

     This version of this YANG module is part of TR-355; see
     the TR itself for full legal notices.";

  revision 2019-05-10 {
    description
      "added leaf server-public-key in
       nokia-software-image-management-extension.yang";       
    reference
      "Nokia specific";
  }

  revision 2018-11-29 {
    description
      "corrected the errors in comment section in
       bbf-software-image-management-one-dot-one-dev.yang file";
    reference
      "Nokia specific";
  }

  revision 2018-09-21 {
    description
      "added base type as failure-reason to identity no-failure";
    reference
      "TBD";
  }

  revision 2016-09-27 {
    description
      "Initial revision.";
    reference
      "TBD";
  }
}
