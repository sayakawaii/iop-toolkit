module nokia-bbf-pppoe-intermediate-agent-l2fwd-fiber-pon-dev {

  namespace
     "urn:bbf:yang:nokia-bbf-pppoe-intermediate-agent-l2fwd-fiber-pon-dev";

  prefix  nokia-bbf-pppoe-intermediate-agent-l2fwd-fiber-pon-dev;

  import bbf-pppoe-intermediate-agent {
    prefix bbf-pppoe-ia;
  }
 
  import ietf-interfaces {
    prefix if;
  }

  import bbf-interface-usage {
    prefix bbf-if-usg;
  }
  
  import bbf-vlan-sub-interface-vector {
	prefix bbf-vsi-vctr;
  }

  organization
    "Nokia";

  contact
    "isam.yang@nokia.com";

  description
    "This module contains a collection of YANG deviations on top 
     of standard for supporting pppoe YANG module.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017-2018, Nokia. All Rights Reserved.";

  /* revision */

  revision 2020-12-09 {
    description
      "Initial revision.";
    reference
      "Nokia specific"; 
  }
 
  /* PPPOE configuration only at user side */
  deviation "/if:interfaces/if:interface/bbf-pppoe-ia:pppoe" {
    deviate add{
        must "(current()/../bbf-if-usg:interface-usage/bbf-if-usg:interface-usage = 'user-port') or (current()/../bbf-if-usg:interface-usage/bbf-if-usg:interface-usage = 'inherit')"
      {
        error-message "PPPOE Relay configuration must be in user port inherit";
      }
    }
  }
  
  deviation "/if:interfaces/if:interface/bbf-pppoe-ia:pppoe" {
      deviate add{
        must "((not(boolean(current()/../bbf-vsi-vctr:vector-profile))))"
		{
			error-message "protocols can be configured only when there is no vector profile attached to vlan-sub-interface.";
		}
	}
}

}
