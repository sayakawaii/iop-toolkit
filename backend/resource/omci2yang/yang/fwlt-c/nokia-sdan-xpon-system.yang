module nokia-sdan-xpon-system {
  yang-version 1.1;
  namespace "http://www.nokia.com/Fixed-Networks/BBA/yang/"+
  "nokia-sdan-xpon-system";

  prefix nokia-sdan-xpon-system;

  import bbf-xpon {
    prefix bbf-xpon;
  }

  organization
    "Nokia";

  contact
    "Comments or questions about this Nokia YANG module should be
     directed to <mailto:isam.yang@nokia.com>.";

  description
    "This specification is published by Nokia under Non-Disclosure
     Agreement(s) (NDA) with specific parties and has to be considered
     as Confidential Information as defined in such NDA. Nokia reserves
     the right to revise this document for any reason, including but
     not limited to conformity with standards promulgated by various
     agencies, utilization of advances in the state of the technical
     areas, or the reflection of changes in the design of any
     equipment, techniques, or procedures described or referred to
     herein.

     The product specifications and other technical or performance
     information contained herein are subject to change without notice.
     Updates of this document will be issued under the above NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising out
     of the sufficiency, accuracy, or utility of any information or
     opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these products
     and to withdraw any or all of them at any future time.

     Copyright (C) 2022, Nokia. All Rights Reserved";

  revision 2026-02-02 {
    description
      "add container dt16-control.";
    reference
      "TBD";
  }

  augment "/bbf-xpon:xpon" {
    description
      "This augment allows to adapt the OLT behaviour for all PON ports,
       to cope with standard non-compliances of some ONUs.";
    
    container dt16-control {
      presence 
        "When present indicates that DT16 special handling is controlled.";
      description
        "Config data nodes to control DT16 special handling so that DT16
         special handling is enabled or disabled.";
      
      leaf avoid-dt16 {
        type boolean;
        default "true";
        description
          "When the data node is 'true', the OLT will avoid allocations 
           to an ONU being spaced exactly 16 frames apart. This may be
           necessary to compensate for the standard non-compliance of 
           some ONUs. Configuring the data node to 'true'  may not be 
           needed nor recommended if only standard compliant ONUs are 
           deployed.";  
        }
    }
  }
}
