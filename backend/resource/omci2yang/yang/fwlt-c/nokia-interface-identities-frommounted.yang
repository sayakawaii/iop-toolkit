module nokia-interface-identities-frommounted {
  yang-version 1.1;
  namespace "http://www.nokia.com/Fixed-Networks/BBA/yang/"
          + "nokia-interface-identities-frommounted";

  prefix nokia-if-id-frommounted;


  import ietf-interfaces-frommounted {
    prefix if-frommounted;
  }

  import iana-if-type-frommounted {
     prefix ianaift-frommounted;
  }

  import bbf-xpon-if-type-frommounted {
    prefix bbf-xponift-frommounted;
  }

  import bbf-moca-if-type-frommounted {
    prefix bbf-mocaift-frommounted;
  }

  organization
    "Nokia";

  contact
    "Comments or questions about this Nokia YANG module should be
     directed to <mailto:isam.yang@nokia.com>.";

  description
    "This module contains a collection of YANG definitions for
     supporting Nokia specific requirements as applicable to its
     access network equipment.

     Specifically, this module defines specialized hardware identities
     to be used in product variants that have pluggable hardware, and/
     or product variants that have specialized ports.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2024-05-22 {
    description
      "Add moca-uni.";
    reference
      "Nokia specific EPIC BBN-729";
  }

  revision 2023-08-31 {
    description
      "Add rf-video-ani and rf-video-uni.";
    reference
      "Nokia specific EPIC BBN-27738";
  }

  revision 2023-06-02 {
    description
      "Creation.";
    reference
      "Nokia specific EPIC BBN-646";
  }

  identity gnss {
    base if-frommounted:interface-type;
    description
      "gnss interface.";
  }

  identity rf-video-uni {
    base ianaift-frommounted:iana-interface-type;
    description
      "RF video UNI for ONU.";
    reference
      "ITU-T G.988 9.13.1 Physical path termination point video UNI.";
  }

  identity rf-video-ani {
    base  bbf-xponift-frommounted:bbf-xpon-interface-type;
    description
      "RF video ANI interface for ONU.";
    reference
      "ITU-T G.988 9.13.2 Physical path termination point video ANI.";
  }
 
  identity moca-uni {
    base bbf-mocaift-frommounted:bbf-moca-interface-type;
    description
      "MoCA UNI for ONU.";
    reference
      "ITU-T G.988 9.10.1 Physical path termination point MoCA UNI.";
  }
}
