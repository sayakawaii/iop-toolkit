module nokia-sdan-hardware-reset-notifications {
  yang-version 1.1;

  namespace "http://www.nokia.com/Fixed-Networks/BBA/yang/"
          + "nokia-sdan-hardware-reset-notifications";

  prefix nokia-sdan-hw-rst-notif;

  import ietf-hardware {
    prefix hw;
  }

  import ietf-yang-types {
    prefix yang;
  }

  import nokia-hardware-identities {
    prefix nokia-hwi;
  }

  organization
    "Nokia";

  contact
     "Comments or questions about this Nokia YANG module should be
     directed to <mailto:isam.yang@nokia.com>.";

  description
     "This module contains a collection of YANG definitions for
     supporting Nokia specific requirements as applicable to its
     access network equipment.

     Specifically, this module defines new reset notifications with
     information about reset type and reason.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2022-11-28 {
    description
      "Initial revision.";
    reference
      "Nokia specific.";
  }

  augment '/hw:hardware-state/hw:component' {
    description
      "Augment the hardware component  with NOKIA specific hardware reset notifications.";

    notification component-reset {
       description
          "Notification to report when hardware component recovered from reset.
           This notification applicable to both operator triggered reset and
           autonomous reset.";

       leaf reset-reason {
          type identityref {
            base nokia-hwi:reset-reason;
          }
          description
           "Indicates reason for hardware component reset.";
       }

       leaf reset-type {
         type identityref {
           base nokia-hwi:reset-type;
         }
         description
           "Indicates reset type of hardware component.";
       }

       leaf reset-info {
         type string;
          description
           "Provides additional information on the reset.";
       }

       leaf reset-triggered-time {
         type yang:date-and-time;
          description
           "Indicates the time the reset was triggered.";
       }

       leaf hardware-ready-time  {
         type yang:date-and-time;
          description
          "Indicates the time when hardware component is ready and operational.";
       }
    }

    notification component-reset-failure {
       description
        "Notification to report failure of hardware reset.";

       leaf failure-reason {
         type string;
          description
          "Indicates reason for reset action failure of hardware component.";
       }
    }
  }
}
