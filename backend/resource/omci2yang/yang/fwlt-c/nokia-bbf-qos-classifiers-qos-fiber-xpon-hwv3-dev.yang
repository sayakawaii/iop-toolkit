module nokia-bbf-qos-classifiers-qos-fiber-xpon-hwv3-dev {

  namespace
    "http://www.nokia.com/Fixed-Networks/BBA/yang/nokia-bbf-qos-classifiers-qos-fiber-xpon-hwv3-dev";

  prefix  nokia-bbf-qos-classifiers-qos-fiber-xpon-hwv3-dev;

  import bbf-qos-classifiers {
    prefix bbf-qos-cls;
  }

  organization
    "Nokia";

  contact
    "isam.yang@nokia.com";

  description
    "This module contains a collection of YANG deviations on top 
     of standard for supporting BBF/bbf-qos-policies YANG module.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017-2018, Nokia. All Rights Reserved.";

  /* revision */
  revision 2026-04-29 {
    description
      "Enable mld on brugal and zacapa board.";
    reference
      "Nokia specific";
  }
  revision 2025-07-06 {
    description
      "Moved from qos-fiber-xpon to free the limitation for LLLT-A";
    reference
      "Nokia specific";
  }

  revision 2024-03-06 {
    description
      "Classifier action pbit/dei index check";
    reference
      "Nokia specific";
  }

  revision 2023-03-14 {
    description
      "Update the supported actions for untagged classifier";
    reference
      "Nokia specific";
  }

  revision 2023-01-11 {
    description
      "Move the dscp-range deviation from whole qos-fiber to only qos-xpon and qos-standalone";
    reference
      "Nokia specific";
  }

  revision 2018-09-06 {
    description
      "removed bbf-qos-filters filter-match restriction.";
    reference
      "Nokia specific";
  }

  revision 2018-02-02 {
    description
      "Initial revision.";
    reference
      "Nokia specific";
  }


  deviation "/bbf-qos-cls:classifiers/bbf-qos-cls:classifier-entry/bbf-qos-cls:filter-method/bbf-qos-cls:inline/bbf-qos-cls:match-criteria/bbf-qos-cls:vlan-tag-match-type/bbf-qos-cls:untagged/bbf-qos-cls:untagged"
  {
    deviate add {
     must "(count(current()/../../bbf-qos-cls:classifier-action-entry-cfg[bbf-qos-cls:action-type = 'bbf-qos-cls:pbit-marking']/bbf-qos-cls:pbit-marking-cfg/bbf-qos-cls:pbit-marking-list) != 0"
        + " and not(count(current()/../../bbf-qos-cls:classifier-action-entry-cfg[bbf-qos-cls:action-type = 'bbf-qos-cls:pbit-marking']/bbf-qos-cls:pbit-marking-cfg/bbf-qos-cls:pbit-marking-list) = 1"
        + " and current()/../../bbf-qos-cls:classifier-action-entry-cfg[bbf-qos-cls:action-type = 'bbf-qos-cls:pbit-marking']/bbf-qos-cls:pbit-marking-cfg/bbf-qos-cls:pbit-marking-list/bbf-qos-cls:index = 1)"
        + " and (count(current()/../../bbf-qos-cls:classifier-action-entry-cfg[bbf-qos-cls:action-type = 'bbf-qos-cls:dei-marking']/bbf-qos-cls:dei-marking-cfg/bbf-qos-cls:dei-marking-list) = 0"
        + " or (count(current()/../../bbf-qos-cls:classifier-action-entry-cfg[bbf-qos-cls:action-type = 'bbf-qos-cls:dei-marking']/bbf-qos-cls:dei-marking-cfg/bbf-qos-cls:dei-marking-list) = 1"
        + " and current()/../../bbf-qos-cls:classifier-action-entry-cfg[bbf-qos-cls:action-type = 'bbf-qos-cls:dei-marking']/bbf-qos-cls:dei-marking-cfg/bbf-qos-cls:dei-marking-list[bbf-qos-cls:index = 0]/bbf-qos-cls:dei-value = 0)"
        + " or (current()/../../bbf-qos-cls:classifier-action-entry-cfg[bbf-qos-cls:action-type = 'bbf-qos-cls:dei-marking']/bbf-qos-cls:dei-marking-cfg/bbf-qos-cls:dei-marking-list[bbf-qos-cls:index = 0]/bbf-qos-cls:dei-value = 0 "
        + " and current()/../../bbf-qos-cls:classifier-action-entry-cfg[bbf-qos-cls:action-type = 'bbf-qos-cls:dei-marking']/bbf-qos-cls:dei-marking-cfg/bbf-qos-cls:dei-marking-list[bbf-qos-cls:index = 1]/bbf-qos-cls:dei-value = 0))"
        + " )"
      {
        error-message "If a classifier matches untagged, it must have pbit-marking-list action and the pbit marking index 0 is mandatory. It may have optional dei-marking-list action, and if it has dei-marking-list, the dei marking index 0 is also mandatory, and marked dei value must be zero for index 0 and 1(if existed).";      
      }
    }
  }

  deviation "/bbf-qos-cls:classifiers/bbf-qos-cls:classifier-entry/bbf-qos-cls:filter-method/bbf-qos-cls:inline/bbf-qos-cls:match-criteria/bbf-qos-cls:protocols/bbf-qos-cls:protocol/bbf-qos-cls:protocol"
  {
    deviate add {
      must "(current() = 'igmp') or (current() = 'mld')"
      {
        error-message "protocol filter only suppport 'igmp' and 'mld'";
      }
    }
  }

}
