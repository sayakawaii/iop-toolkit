module nokia-sdan-olt-v-enet-cfm-hostid-dev {

  namespace "http://www.nokia.com/Fixed-Networks/BBA/yang/" +
            "nokia-sdan-olt-v-enet-cfm-hostid-dev";

  prefix nokia-sdan-olt-v-enet-cfm-hostid-dev;

  import ietf-interfaces {
    prefix if;
  }

  import bbf-xponvani{
    prefix bbf-xponvani;
  }

  import nokia-sdan-olt-v-enet {
    prefix nokia-olt-v-enet;
  }

  organization
    "Nokia";

  contact
    "isam.yang@nokia.com";

  description
    "This module contains a collection of YANG deviations on top
     of standard for supporting YANG module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2017-2018, Nokia. All Rights Reserved.";

  revision 2022-09-29 {
    description
      "Initial revision.";
    reference
      "Nokia specific";
  }

  deviation "/if:interfaces/if:interface/bbf-xponvani:olt-v-enet/"
          + "nokia-olt-v-enet:v-ethernet-id" {
    description
      "CFM uses MAC address generated from the v-ethernet-id
       configured for the olt-v-enet interface. This olt-v-enet
       interface is the lower layer interface of the user-port
       vlan-sub-interfaces referenced by the maintenance-group
       forwarder ports or maintenance end points of CFM.

       The error message, 'User vlan-sub-interface with a CFM MEP/MIP
       must have a olt-v-enet v-ethernet-id' will be displayed when
       v-ethernet-id is removed for the inteface whose higher layer
       user-port vlan-sub-interface has a CFM maintenance point.";
    deviate add {}
  }
}
