submodule bbf-sip-server-frommounted {
  yang-version 1.1;
  belongs-to bbf-sip-voip-frommounted  {
    prefix bbf-sip-voip-frommounted;
  }
  
  import ietf-inet-types {
    prefix inet;
	reference
      "RFC 6991: Common YANG Data Types.";
  }
  
  include bbf-sip-types-frommounted;
  
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains a collection of YANG definitions for
     managing the first hop Sip server profiles and their settings.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2023-01-06 {
    description
      "update description";
  }

  revision 2020-03-06 {
    description
      "Initial revision.
       * Approval Date:    see revision date above.
       * Publication Date: 2020-03-06.";
    reference
      " ";
  }
  
  typedef transport {
	type bits {
	  bit udp {
	  	position 0;
	  	description
	  	  "Underlying transport protocol for 
	  	   SIP is UDP.";
	  }
	  bit tcp {
	  	position 1;
	  	description
	  	  "Underlying transport protocol for
	  	   SIP is TCP.";
	  }
	  bit tlsotcp {
	  	position 2;
	  	description
	  	  "Underlying transport protocol for
	  	   SIP is TLSoTCP.";
	  }
	}
	description
	  "The underlying transport protocol for SIP signaling.";
  }

  grouping sip-server-characteristics {    
    container session-timer {
      presence "session-timer";
	  description
		"The SIP session timer nodes.";
	  leaf session-expiry {
        type uint16 {range "90..65535";}
        units seconds;
        description
        "The SIP session expiry time.";
      }	  
      leaf minimum-session-expiry {
        type uint16 {range "90..65535";}
        units "1 sec";
		description
          "The minimum session Expiry time.";
      }      
      leaf enabled-by-uac {
        type boolean;
        description
          "The session expiry is requested in the initial
           SIP INVITE requests and the 200 OK responses to 
           the SIP INVITE requests. In case an incoming 
           initial SIP INVITE request contains a session 
           expiry header, but does not include the refresher
           value, the refresher parameter is set to UAC.";
      }
      leaf enabled-by-uas {
        type boolean;
        description
          "The session expiry is requested in the initial 
          SIP INVITE requests and the 200 OK responses to 
          the SIP INVITE requests. In case an incoming 
          initial SIP INVITE request contains a session 
          expiry header, but does not include the refresher
          value, the refresher parameter is set to UAS.";
      }     
    } 	
	leaf pots-user-itf-syntax {
      description
      	"POTS User interface syntax pattern.";  
      type enumeration {
        enum uri-or-dn {
          value 1;
		  description
      	  	"The pattern is a URI or DN.";
        }
		enum physical-itf-dn {
	      value 2;
		  description
      	  	"The pattern is the physical 
      	  	 interface identifier.";
        }
		enum random-per-register-request {
	      value 3;
		  description
      	  	"The pattern is a random value per SIP
      	  	 Register request.";
        }
		enum random-per-register-and-dialog {
	      value 4;
		  description
      	    "The pattern is a random value per SIP
      	     Register and SIP dialog request.";
        }
	  }
    } 
    leaf pots-user-interface-id {
      type string {length "1..128";}
      description
      	"The POTS user interface syntax.";
    }
	
  } 	
  
  grouping sip-server {     
    container sip-server-address {
      presence "sip-server-address";
      description
        "The address type of the first hop SIP server.";
      leaf address-type {
		type enumeration {
		  enum ip {
		    value 1;
		    description
            "The address type of the first hop SIP server is an 
             IP address.";
		  }
		  enum fqdn {
		    value 2;
		    description
            "The address type of the first hop SIP server is a 
             fully qualified domain name.";
		  }
          enum srv {
		    value 3;
		    description
            "The address type of the first hop SIP server is a 
             service record name.";
		  }
		  enum dn {
		    value 4;
		    description
            "The address type of the first hop SIP server is a 
             domain name.";
		  }
		}
        description
          "The address type of the first hop SIP server.";
	  }
	  container ip {
     presence "ip";
        description
          "The first hop server address is an IP address.";
        leaf ip-address {
          type inet:ip-address;
          description
            "The IP address of the first hop SIP server.";
        }	  
	  }
	  container fully-qualified-domain {
     presence "fully-qualified-domain";
		description
      	  "The first hop server address is a fully qualified
      	  domain name.";
		leaf fully-qualified-domain-name {
          type string
          {
            length "0..100";
          }
          description
            "The FQDN address of the first hop SIP server.";
        }  		  
	  }
    }
    leaf sip-server-role {
      type bits {
        bit proxy {
          position 0;
          description
          	"SIP proxy server.";
        }
        bit registrar {
          position 1;
          description
          	"SIP registrar.";
        }
        bit outbound-proxy {
          position 2;
          description
          	"Outbound proxy SIP server.";
        }
        bit back-to-back {
          position 3;
          description
          	"SIP back-to-back server.";
        }
        bit session-border-controller {
          position 4;
          description
          	"Session border controller.";
        }
        bit emergency-stand-alone {
          position 5;
          description
          	"Emergency Stand-alone SIP server.";
        }
        bit local-stand-alone {
          position 6;
          description
          	"Local Stand-alone SIP server.";
        }
      }	  
      description
      	"The role to be fulfilled by the first hop SIP server.";
    }		      	  	  
  }   
}
