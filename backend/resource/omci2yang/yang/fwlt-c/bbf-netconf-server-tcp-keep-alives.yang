module bbf-netconf-server-tcp-keep-alives {
  yang-version 1.1;
  namespace "urn:broadband-forum-org:yang:bbf-netconf-server-tcp-keep-alives";
  prefix bbf-ncs-tcpka;

  import ietf-netconf-server {
    prefix "ncs";
  }

  organization
    "Broadband Forum <https://www.broadband-forum.org>
     Common YANG Work Area";

  contact
    "Comments or questions about this Broadband Forum YANG module
     should be directed to <mailto:help@broadband-forum.org>.

     Editor:      Joey Boyd, ADTRAN

     Editor:      Ludwig Pauwels, Nokia

     WA Director: Sven Ooghe, Nokia

     WA Director: Joey Boyd, ADTRAN";

  description
    "This module contains a collection of YANG definitions that are
     used to configure TCP keep-alives for a call-home collection.
     When a server implements this module, only TCP keep-alive is
     supported and the configuration of the keep-alives in the 
     security layer in container 'keep-alives' in module 
     'ietf-netconf-server' is ignored.

     Copyright (c) 2018, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please  reference the Forum IPR Policy for patent licensing terms
     <https://www.broadband-forum.org/ipr-policy>.

     Any moral rights which are necessary to exercise under the above
     license grant are also deemed granted under this license.

     This version of this YANG module is part of TR-383; see
     the TR itself for full legal notices.";

  revision 2018-08-31 {
    description
      "Initial revision.";
    reference
      "TR-383: Common YANG Modules
               <https://www.broadband-forum.org/technical/download/
                        TR-383.pdf>";
  }

  augment
    "/ncs:netconf-server/ncs:call-home/ncs:netconf-client" +
    "/ncs:connection-type/ncs:connection-type" +
    "/ncs:persistent-connection/ncs:persistent" {
    description
      "Augments the configuration of a call-home connection-type
       with the configuration of TCP keep-alives.";
    container tcp-keep-alives {
      presence "Enables the configuration of TCP keep-alives";
	  description
        "Configures the keep-alive policy to proactively test the 
         aliveness of the TCP peer. An unresponsive TCP peer is 
         recommended to be dropped after approximately 'max-wait' 
         plus 'max-attempts' * 'interval-between-attempts' seconds.";
      reference
        "RFC 1122: Requirements for Internet Hosts --
         Communication Layers, section 4.2.3.6.";
      leaf max-wait {
        type uint16 {
          range "1..32767";
        }
        units seconds;
        default 30;
        description
          "Sets the amount of time in seconds, after which, if no 
           data has been received from the TCP peer, a TCP-level 
           message will be sent to test the aliveness of the TCP 
           peer.";
      }
      leaf max-attempts {
        type uint8 {
          range "1..127";
        }
        default 3;
        description
          "Sets the maximum number of sequential keep-alive messages 
           that can fail to obtain a response from the TCP peer 
           before assuming the TCP peer is no longer alive.";
      }
      leaf interval-between-attempts {
        type uint16  {
          range "1..32767";
        }
        units seconds;
        default 30;
        description
          "Sets the amount of time in seconds, after which, if no 
           reply to a keep-alive message has been received from the 
           TCP peer, the next keep-alive message will be sent.";
      }
    } // container tcp-keep-alives
  } // augment
}
