module nokia-ipv6-address-spoofing-prevention-ipv6-antispoofing-fiber-dev {

  namespace "http://www.nokia.com/Fixed-Networks/BBA/yang/"
          + "nokia-ipv6-address-spoofing-prevention-ipv6-antispoofing-fiber-dev";

  prefix nokia-ipv6-address-spoofing-prevention-ipv6-antispoofing-fiber-dev;

  import ietf-interfaces {
    prefix if;
  }

  import nokia-ipv6-address-spoofing-prevention {
    prefix nokia-ipv6-sppr;
  }

  import bbf-vlan-sub-interface-vector {
	prefix bbf-vsi-vctr;
  }

  import nokia-vlan-sub-interface-vector-ipv6-address-spoofing-prevention {
	prefix nokia-vector-ipv6-sppr;
  }

  organization
    "Nokia";

  contact
    "Comments or questions about this Nokia YANG module should be
     directed to <mailto:isam.yang@nokia.com>.";

  description
    "This module contains a collection of YANG definitions for
     supporting Nokia specific requirements as applicable to its
     access network equipment.

     Specifically, this module provides restrictions (=deviations) for
     the implementation in the ISAM ?????.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2018, Nokia. All Rights Reserved.";

  revision 2020-09-30 {
    description
      "Initial revision.";
    reference
      "Nokia specific";
  }

  deviation "/if:interfaces/nokia-ipv6-sppr:ipv6-security-statistics"
           +"/nokia-ipv6-sppr:interface/nokia-ipv6-sppr:name"  {
    deviate add {
          must
            "((/if:interfaces/if:interface[if:name = current()]"
           +"/nokia-ipv6-sppr:ipv6-security/nokia-ipv6-sppr:"
           +"prevent-ipv6-address-spoofing = 'true') or"
           +"(/bbf-vsi-vctr:vsi-vector-profiles/bbf-vsi-vctr:vsi-vector-profile[bbf-vsi-vctr:name=/if:interfaces/if:interface[if:name = current()]/bbf-vsi-vctr:vector-profile]"
           +"/nokia-vector-ipv6-sppr:ipv6-security/nokia-vector-ipv6-sppr:prevent-ipv6-address-spoofing = 'true'))" {
           error-message "Before enable ipv6-security-statistics,prevent-ipv6-address-spoofing should be enabled;
                     Before disable prevent-ipv6-address-spoofing ,ipv6-security statistics should be disabled.";
           description "Before enable ipv6-security-statistics,prevent-ipv6-address-spoofing should be enabled";
          }
    }
  }

  deviation "/nokia-ipv6-sppr:ipv6-antispoofing-system"
            +"/nokia-ipv6-sppr:clear-dhcp-learned-ipv6-addresses-on-operdown"
  {
    
     description
             "indicated that clear-dhcp-learned-ipv6-address-on-operdown not supported";
     deviate not-supported;

  }

  deviation "/if:interfaces/if:interface/nokia-ipv6-sppr:ipv6-security"
            +"/nokia-ipv6-sppr:prevent-ipv6-address-spoofing"
  {
     description
         "To remove default value false from leaf prevent-ipv6-address-spoofing on fiber platform";
     deviate delete {
        default "false";
     }
     
  }


  deviation "/if:interfaces/if:interface/nokia-ipv6-sppr:ipv6-security/nokia-ipv6-sppr:static-ipv6-address" {
      deviate add {
        must "((current()/../nokia-ipv6-sppr:prevent-ipv6-address-spoofing = 'true'))" {
              error-message "Before create ipaddress,prevent-ipv6-address-spoofing should be enabled;
              Before disable prevent-ipv6-address-spoofing, ipaddress should be deleted";
              description "Before create ipaddress,prevent-ipv6-address-spoofing should be enabled";
          }
      }
  }

}
