submodule bbf-sip-profiles-mounted {
  yang-version 1.1;
  belongs-to bbf-sip-voip-mounted  {
	prefix bbf-sip-voip-mounted;
  }

  import bbf-yang-types {
    prefix bbf-yang;
  }

  import bbf-fiber-onu-emulated-mount {
     prefix onu;
  }
  
  include bbf-sip-voip-base-mounted;
  include bbf-dialplan-digitmap-profile-body-mounted;
  include bbf-digit-manipulation-rule-profile-body-mounted;
  include bbf-supplementary-services-profile-body-mounted;
  include bbf-feature-access-codes-profile-body-mounted;
  include bbf-subscription-profile-body-mounted;
  include bbf-sip-registerchar-profile-body-mounted;
  include bbf-sip-protocol-data-profile-body-mounted;
  
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains the Yang definitions for the sip 
	 profiles.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2020-03-06 {
    description
      "Initial revision.
       * Approval Date:    see revision date above.
       * Publication Date: 2020-03-06.";
    reference
      " ";
  }
   
  
  grouping suppl-services-conf {
    list supplementary-services-profile {
      key "name";
      description
        "A list of POTS sip user supplementary services profiles.";
      leaf name {
        type bbf-yang:string-ascii64;
   	    description
   	      "The name of the call services profile.";
      }  
      uses supplementary-services-profile-body;
    }
  }
  
  augment "/onu:onus/onu:onu/onu:root/bbf-sip-voip-mounted:sip-profiles"
        + "/bbf-sip-voip-mounted:supplementary-services-profiles" {
    uses suppl-services-conf; 
  } 
  
  grouping digit-manipulation-rule-conf {
    list digit-manipulation-rule-profile {
      key "name";
      description
        "A digit manipulation rule profile.";
      leaf name {
        type bbf-yang:string-ascii64;	
 	    description
          "Uniquely identifies the profile.";
      }
      uses digit-manipulation-rule-profile-body;
    }
  }
  
  augment "/onu:onus/onu:onu/onu:root/bbf-sip-voip-mounted:sip-profiles"
        + "/bbf-sip-voip-mounted:digit-manipulation-rule-profiles" {
  if-feature digit-manipulation;
    uses digit-manipulation-rule-conf; 
  }   

  /* typedef dialplan-digitmap-ref {
    type leafref {
 	  path "/bbf-sip-voip-mounted:sip-profiles"
         + "/bbf-sip-voip-mounted:dialplan-digitmap-profiles"
		 + "/bbf-sip-voip-mounted:dialplan-digitmap-profile"
		 + "/bbf-sip-voip-mounted:name";	
	}
	description
	  "References a dialplan digitmap profile.";
  } */
  
  grouping dialplan-digitmap-conf {
    list dialplan-digitmap-profile {
      key "name";    
	  description
        "A list of dialplan and digitmap profiles.";
      leaf name {
        type bbf-yang:string-ascii64;    
	    description
    	    "Uniquely identifies the dialplan and digitmap profile.";
      }
      uses dialplan-digitmap-profile-body;
    }
  } 
  
  augment "/onu:onus/onu:onu/onu:root/bbf-sip-voip-mounted:sip-profiles" 
        + "/bbf-sip-voip-mounted:dialplan-digitmap-profiles" { 
    uses dialplan-digitmap-conf;
  }
  
  grouping subscription-conf {
    list subscription-profile {
	  key "name";
	  leaf name {
	    type bbf-yang:string-ascii64;
	    description
          "The name of the Voip Service Provider subscription
 		   profile.";
      }
	  uses subscription-profile-body;
	}
  }
  
  augment "/onu:onus/onu:onu/onu:root/bbf-sip-voip-mounted:sip-profiles"
        + "/bbf-sip-voip-mounted:subscription-profiles" {
  if-feature subscriptions;
    uses subscription-conf; 
  }   
 
  grouping feature-access-code-conf {
    list feature-access-codes-profile {
      key "name";    
	  description
        "A feature access codes.";
      leaf name {
        type bbf-yang:string-ascii64;		
 	    description
       	  "Uniquely identifies the profile.";
      }
      uses feature-access-codes-profile-body;
    }	
  }
  
  augment "/onu:onus/onu:onu/onu:root/bbf-sip-voip-mounted:sip-profiles"
        + "/bbf-sip-voip-mounted:feature-access-codes-profiles" {
    uses feature-access-code-conf; 
  } 
  
  grouping registerchar-conf {
    list sip-registerchar-profile {
      key "name";
      description
        "A register method properties profile.";
      leaf name {
        type bbf-yang:string-ascii64;
        description
         "The name of the register method properties profile.";
      }	  
      uses sip-registerchar-profile-body;
    }   	
  } 
  
  augment "/onu:onus/onu:onu/onu:root/bbf-sip-voip-mounted:sip-profiles"
        + "/bbf-sip-voip-mounted:sip-registerchar-profiles" {
    uses registerchar-conf; 
  }
  
  grouping protocol-data-conf {
    list sip-protocol-data-profile {
      key "name";
      description
        "A SIP protocol data profile.";
      leaf name {
        type bbf-yang:string-ascii64;
        description
         "The name of the SIP protocol data profile.";
      }	  
      uses sip-protocol-data-profile-body;
    }   	
  } 
  
  augment "/onu:onus/onu:onu/onu:root/bbf-sip-voip-mounted:sip-profiles"
        + "/bbf-sip-voip-mounted:sip-protocol-data-profiles" {
    uses protocol-data-conf; 
  }  
}
