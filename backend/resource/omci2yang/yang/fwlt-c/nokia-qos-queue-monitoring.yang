module nokia-qos-queue-monitoring {
  yang-version 1.1;  
  namespace "http://www.nokia.com/Fixed-Networks/BBA/yang/"
          + "nokia-qos-queue-monitoring";
  
  prefix nokia-queue-mon;

  import ietf-interfaces {
    prefix if;
  }

  import ietf-yang-types {
    prefix yang;
  }

  import bbf-interfaces-performance-management {
    prefix bbf-if-pm;
  }
  import bbf-yang-types {
    prefix bbf-yang;
  }
  
  import bbf-qos-traffic-mngt {
    prefix bbf-qos-tm;
  }

  import ietf-netconf-acm {
    prefix nacm;
  }
 
  organization
    "Nokia";

  contact
    "Comments or questions about this Nokia YANG module should be 
     directed to <mailto:isam.yang@nokia.com>.";

  description
    "This module contains a collection of YANG definitions for 
     supporting Nokia specific requirements as applicable to its 
     access network equipment.
     
     Specifically, this module adds configuration and state data for 
     QoS queue monitoring which includes statistics and history 
     performance monitoring data.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these 
     products and to withdraw any or all of them at any future time.

     Copyright (C) 2017, Nokia. All Rights Reserved.";

  revision 2018-10-25 {
    description
      "Added color based counter";
    reference
      "Nokia specific";  
  }

  revision 2018-09-07 {
    description
      "Added nacm:default-deny-all for action clear-statistics";
    reference
      "Nokia specific";  
  }

  revision 2017-08-01 {
    description
      "Initial revision.
       * Approval Date:    see revision date above.
       * Publication Date: yyyy-mm-dd.";
    reference
      "Nokia specific";
  }

  feature queue-statistics {
    description
      "Indicates that collection of statistics (i.e. rolling counters)
       is supported for queue monitoring.";
  }

  feature queue-performance-24hr {
    description
      "Indicates that collection of 24 hour performance intervals
       is supported for queue monitoring.";
  }

  feature queue-performance-15min {
    description
      "Indicates that collection of 15 minutes performance intervals
       is supported for queue monitoring.";
  }

  feature queue-color-counter {
    description
      "Indicates that color based collection is supported for queue 
       monitoring.";
  }
 
  grouping queue-counters {
    description
      "Queue counters associated with performance counters and 
       statistics.";
                
    leaf out-pkts {
      type bbf-yang:performance-counter64;
      description
        "Number of packets transmitted from the queue.";
    }
        
    leaf out-octets {
      type bbf-yang:performance-counter64;
      description
        "Number of octets transmitted from the queue.";
    }
    
    leaf drop-pkts {
      type bbf-yang:performance-counter64;
      description
       "Total number of packets that were addressed to the queue, but 
        that were dropped instead of being queued, e.g. because of 
        buffer overflow.";
    }
  
    leaf drop-octets {
      type bbf-yang:performance-counter64;
      description
        "Total number of octets that were addressed to the queue, but 
         that were dropped instead of being queued, e.g. because of 
         buffer overflow.";
    }
  }
  
  grouping queue-performance-counters {
    description
      "Queue counters associated with current and historical 15 minute
       and 24 hour performance counters.";
                
    uses queue-counters;
  
    container color {
      if-feature "queue-color-counter";
      description
      "A color based collection of queue performace.";
  
      container green {
        description 
          "Green packets.";
  
        uses queue-counters;
      }
  
      container yellow {
        description 
          "Yellow packets.";
  
        uses queue-counters;
      }
  
      container red {
        description 
         "Red packets.";
  
        uses queue-counters;
      }
    }
  }
  
  grouping queue-statistics {
    description 
      "A collection of queue-related statistics objects.";

    container statistics {
      if-feature "queue-statistics";
      description
        "A collection of queue-related statistics objects.";
    
      uses queue-counters;

      container color {
        if-feature "queue-color-counter";
        description
          "A color based collection of queue statistics.";

        container green {
          description 
            "Green packets.";

          uses queue-counters;
        }

        container yellow {
          description 
            "Yellow packets.";

          uses queue-counters;
        }

        container red {
          description 
            "Red packets.";

          uses queue-counters;
        }
      }  
    }              
  }
  
  grouping queue-monitoring {
    description
      "Data nodes for queue monitoring configuration parameters.";

    container queue-monitoring {
      description
        "Queue monitoring configuration parameters.";

      leaf enable-statistics {
        if-feature "queue-statistics";
        type boolean;
        default "false";
        description 
          "If true, enables counting of queue statistics.
           Then queue statistics will be available in
           /interfaces-state/interface/bbf-qos-mon:tm-root. 
           If false then there are no queue statistics.";
      }
        
      leaf enable-performance {
        if-feature "queue-performance-15min or 
                    queue-performance-24hr";
        type boolean;
        default "false";
        description 
          "If true, enables counting of queue performance.
           Then performance counters will be available in
           /interfaces-state/interface/bbf-qos-mon:tm-root.
           i.e. 15 minutes and 24 hours counters, 
           and for both there are current counters and history 
           counters.
           If false then there are no queue performance counters.";
      }
    }         
  }
  
  augment '/if:interfaces/if:interface/bbf-qos-tm:tm-root'
        + '/bbf-qos-tm:children-type/bbf-qos-tm:queues' {
    description
      "Data nodes for queue monitoring configuration parameters.";

    uses queue-monitoring;    
  } 
  
  grouping queue-performance {
    description 
      "Queue performance counters.";  
    container performance {
      description
        "Performance parameters.";
                
      container intervals-15min {
        if-feature "queue-performance-15min";
        description
          "15min intervals performance counters.";
                  
        container current {
          description
            "Contains the current 15min queue accumulating counters.";
          uses queue-performance-counters;
        }

        uses bbf-if-pm:performance-15min-history-parameters;

        list history {
          key "interval-number";
          max-elements 96;
          description
            "A history of 15 minute intervals.";

          leaf interval-number {
            type bbf-if-pm:performance-15min-history-interval;
            description
              "The number of the interval relative to the current
               interval.";
          }

          uses 'bbf-if-pm:performance-history-15min-interval-'
             + 'parameters';         
          uses queue-performance-counters;      
        }
      }
   
      container intervals-24hr {
        if-feature "queue-performance-24hr";
        description
          "24 hour interval performance history";

        container current {
          description
            "Contains the current 24 hour queue accumulating 
             counters.";

          uses queue-performance-counters;
        }

        uses bbf-if-pm:performance-24hr-history-parameters;

        list history {
          key "interval-number";
          max-elements 2;
          description
            "A history of 24 hour intervals.";

          leaf interval-number {
            type bbf-if-pm:performance-24hr-history-interval;
            description
              "The number of the interval relative to the current
               interval.";
          }

          uses bbf-if-pm:performance-history-24hr-interval-parameters;
          uses queue-performance-counters;
        }
      }  
    } 
  }

  grouping tm-root {
    description
      "This node represents traffic management data counters.";

    container tm-root {
      description
        "The attributes of the root in the tree.";

      action clear-statistics {
        nacm:default-deny-all;
        if-feature "queue-statistics";
        description
          "When the action is received, the statistics within the 
           traffic management root are cleared.";
      }

      leaf discontinuity-time {
        if-feature "queue-statistics";
        type yang:date-and-time;
        description
           "The time on the most recent occasion at which any one or
           more of this tm-root node queue counters suffered a
           discontinuity.  If no such discontinuities have occurred
           since the last re-initialization of the local management
           subsystem, then this node contains the time the local
           management subsystem re-initialized itself.";
      }

      choice children-type{
        description
          "Choice of chidren types of a queue and scheduler node.";
  
        case queues { 
          description
            "Operational data for queues in the TM root.";
    
          list queue {
            key "local-queue-id";
            description
              "A list of queues.";
                          
            leaf local-queue-id {
              type bbf-qos-tm:queue-id;
              description
                "The identification of a queue within the context of 
                 this list.";
            }
                
            uses queue-statistics;
            uses queue-performance;
          }
        }
      }
    }
  }

  augment '/if:interfaces-state/if:interface' {                 
    description
      "Augments interfaces-state with traffic management state data 
       such as statistics and history performance monitoring 
       counters.";
    
    uses tm-root;
  }   
}
