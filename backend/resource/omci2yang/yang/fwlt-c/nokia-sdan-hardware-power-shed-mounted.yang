module nokia-sdan-hardware-power-shed-mounted {
  yang-version 1.1;
  namespace "http://www.nokia.com/Fixed-Networks/BBA/yang/"
             + "nokia-sdan-hardware-power-shed-mounted";
  prefix nokia-hw-pwr-shed-mounted;

  import ietf-hardware-mounted {
    prefix hw-mounted;
  }

  import iana-hardware {
    prefix ianahw;
  }

  import nokia-sdan-hardware-power-shed-profiles-mounted {
    prefix nokia-hw-pwr-shed-prof-mounted;
  }
  
  import bbf-fiber-onu-emulated-mount {
     prefix onu;
  }
  
  organization
    "Nokia";

  contact
    "Comments or questions about this Broadband Forum YANG module
     should be directed to <mailto:isam.yang@nokia.com>.";

  description
    "This module contains a collection of YANG definitions for
     power management.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2024-09-11 {
    description
      "remove operational data related when statement";
    reference
      "BBN-107706";
  }

  revision 2022-01-18 {
    description
      "Initial revision.";
    reference
      "tbc";
  }

  augment "/onu:onus/onu:onu/onu:root/hw-mounted:hardware/hw-mounted:component" {
    when "derived-from-or-self(hw-mounted:class, 'ianahw:chassis')" {
      description
        "Only applicable to device chassis component.";
    }
    description
      "Augments the device chassis with the capability to manage
       power shedding function when the device enters battery 
       backup operation mode after AC power failure.";
    container power-shedding {
      presence
        "The presence of this container enables the configuration
         of power shedding data nodes at chassis level.";     
      description
        "Configuration power shedding data nodes at chassis 
         level.";
      leaf power-shedding-profile-ref {
        type leafref {
          path "../../../../nokia-hw-pwr-shed-prof-mounted:power-shedding-profiles/"
               + "nokia-hw-pwr-shed-prof-mounted:power-shedding-profile/"
               + "nokia-hw-pwr-shed-prof-mounted:name";
        }
        description
          "Reference to power shedding profile.";
      }
      leaf backup-battery-monitoring {
        type enumeration {
          enum disabled {
            description
              "Disables ONU from monitoring the backup battery 
               and generating battery related alarms.";          
          }
          enum enabled {
            description
              "Enables ONU to monitor the backup battery and 
               generate battery related alarms, if it has the 
               capability to do so.";
          }
        }
        default disabled;
        description
          "Controls whether the ONU can monitor the backup 
           battery and report battery related alarms.";
        reference 
          "ITU-T G.988 9.1.1 ONU-G: Battery backup";
      }
    }
  }

  augment "/onu:onus/onu:onu/onu:root/hw-mounted:hardware/hw-mounted:component" {
    when "derived-from-or-self(hw-mounted:class, 'ianahw:port')"{
      description
        "Only applicable to device port component.";
    }
    description
      "Augments the device port with the capability to manage power
       shedding function when the device enters battery backup 
       operation mode after AC power failure.";
    container port-power-shedding {
      presence 
        "The presence of this container enables the configuration
         of power shedding data nodes at port level.";  
      description
        "Configuration power shedding data nodes at port level.";
      leaf power-shed-override {
        type boolean;
        default false;
        description
          "When true, prevents the port to be subjected to power
           shedding. When false, allows the port to be subjected to 
           power shedding control, per chassis configuration.";
	    reference 
	      "ITU-T G.988 9.1.6 Circuit pack: Power shed override";
      }
    }
  }
  
  augment "/onu:onus/onu:onu/onu:root/hw-mounted:hardware-state/hw-mounted:component" {
    description
      "Augments the device chassis with the capability to monitor
       power shedding state.";
    leaf power-shed-state {
      type bits {
        bit data-class {
          position 0;
          description
            "Related to data service.";
        }
        bit voice-class {
          position 1;
          description
            "Related to voice service.";
        }
        bit video-overlay-class {
          position 2;
          description
            "Related to video-overlay service.";
        }
        bit video-return-class {
          position 3;
          description
            "Related to video-return service.";
        }
        bit dsl-class {
          position 4;
          description
            "Related to dsl service.";
        }
        bit atm-class {
          position 5;
          description
            "Related to atm service.";
        }
        bit ces-class {
          position 6;
          description
            "Related to ces service.";
        }
        bit frame-class {
          position 7;
          description
            "Related to frame service.";
        }
        bit sdh-sonet-class {
          position 8;
          description
            "Related to sdh-sonet service.";
        }
      }
      description
        "Indicates power shedding status. A bit of value 1 indicates
         the power shedding is active for the corresponding service";
      reference 
	    "ITU-T G.988 9.1.7 ONU power shedding: Shedding status";
    }
  }
}
