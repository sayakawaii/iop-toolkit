module nokia-yang-types {

  namespace "http://www.nokia.com/Fixed-Networks/BBA/yang/"
          + "nokia-yang-types";

  prefix  nok-typ;

  organization
    "Nokia";

  contact
    "Comments or questions about this Nokia YANG module should be 
     directed to <mailto:isam.yang@nokia.com>.";

  description
    "This module contains a collection of YANG definitions for 
     supporting Nokia specific requirements as applicable to its 
     access network equipment.
     
     Specifically, this module provides type definitions used in
     Nokia specific modules.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2023, Nokia. All Rights Reserved.";

 revision 2023-09-01 {
    description
      "add nokia-string-ascii100-empty type";
    reference
      "Nokia specific";
  }

 revision 2023-08-29 {
    description
      "add nokia-string-ascii100 type";
    reference
      "Nokia specific";
  }
  
 revision 2023-02-22 {
    description
      "update nokia-string type description";
    reference
      "Nokia specific";
  }

 revision 2021-06-07 {
    description
      "Added nokia-string-ascii1024";
    reference
      "Nokia specific Epic BBN-555";
  }

 revision 2020-06-19 {
    description
      "Extend with time of day";
    reference
      "Nokia specific";
  }

  revision 2020-03-11 {
    description
      "Escaped ^ to make it normal literal in the pattern";
    reference
      "Nokia specific";
  }

  revision 2019-07-10 {
        description
	        "Extend the allowed character set.";
          reference
            "Nokia specific"; 
  }

  revision 2018-12-03 {
    description
      "Initial revision.";
    reference
      "Nokia specific"; 
  }

  typedef nokia-string-ascii63-or-empty {
    type string {
      length "0..63";
      pattern '[!#&-Z\^_-z|~]*';
    }
    description
      "Used where a string is needed which has a maximum length of 
       63 characters and also allows for a null string (length = 0).

       The character set is a Nokia limited subset of the 95 printable
       ASCII characters.
       
       The intended use is to use everywhere BBF uses the type 
       string-ascii63-or-empty.";
  }

  typedef nokia-string-ascii64 {
    type string {
      length "1..64";
      pattern '[!#&-Z\^_-z|~]*';
    }
    description
      "Used where a string is represented using at least 1 and no more
       than 64 ASCII characters.

       The character set is a Nokia limited subset of the 95 printable
       ASCII characters.
       
       The intended use is to use everywhere BBF uses the type 
       string-ascii64 or type name-string, or where IETF uses the type 
       string and the leaf the parameter is mandatory.";
  }

  typedef nokia-string-ascii100 {
    type string {
      length "1..100";
      pattern '[!#&-Z\^_-z|~]*';
    }
    description
      "Used where a string is represented using at least 1 and no more
       than 100 ASCII characters.

       The character set is a Nokia limited subset of the 95 printable
       ASCII characters.

       The intended use is to use everywhere BBF uses the type
       string-ascii100 or type name-string, or where IETF uses the type
       string and the leaf the parameter is mandatory.";
  }

  typedef nokia-string-ascii100-or-empty {
    type string {
      length "0..100";
      pattern '[!#&-Z\^_-z|~]*';
    }
    description
      "Used where a string is needed which has a maximum length of
       100 characters and also allows for a null string (length = 0).
       
       The character set is a Nokia limited subset of the 95 printable
       ASCII characters.
       
       The intended use is to use everywhere BBF uses the type 
       string-ascii100-or-empty, or where IETF uses the type string and
       the leaf is optional.";
  }
  
  typedef nokia-string-ascii64-or-empty {
    type string {
      length "0..64";
      pattern '[!#&-Z\^_-z|~]*';
    }
    description
      "Used where a string is needed which has a maximum length of
       64 characters and also allows for a null string (length = 0).
       
       The character set is a Nokia limited subset of the 95 printable
       ASCII characters.
       
       The intended use is to use everywhere BBF uses the type 
       string-ascii64-or-empty, or where IETF uses the type string and
       the leaf is optional.";
  }
 typedef nokia-string-ascii1024-or-empty {
    type string {
      length "0..1024";
      pattern '[!#&-Z\^_-z|~ ]*';
    }
    description
      "Used where a string is needed which has a maximum length of
       1024 characters and also allows for a null string (length = 0).

       The character set is a Nokia limited subset of the 95 printable
       ASCII characters.

       The intended use is to use where IETF uses the type string and the leaf parameter is optional.";
  }

typedef nokia-string-ascii1024 {
    type string {
      length "1..1024";
      pattern '[!#&-Z\^_-z|~ ]*';
    }
    description
      "Used where a string is represented using at least 1 and no more
       than 1024 ASCII characters.

       The character set is a Nokia limited subset of the 95 printable
       ASCII characters.

       The intended use is to use where IETF uses the type
       string and the leaf parameter is mandatory.";
  }

 typedef nokia-time-of-day {
    type string {
      length "8";
      pattern "([0-1][0-9]|2[0-3]):[0-5][0-9]:[0-5][0-9]" {
        error-message "The time format is 'hour:minute:second'. The range of hours is 00 to 23. The range of minutes and seconds is 00 to 59.";
      }
    }
    description "The time of day in 24 hour format.";
  }
}
