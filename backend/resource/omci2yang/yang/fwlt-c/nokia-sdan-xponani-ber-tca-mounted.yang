module nokia-sdan-xponani-ber-tca-mounted {
  yang-version 1.1;

  namespace "http://www.nokia.com/Fixed-Networks/BBA/yang/"
  + "nokia-sdan-xponani-ber-tca-mounted";

  prefix nokia-sdan-xponani-ber-tca-mounted;

  import ietf-interfaces-mounted {
    prefix if-mounted;
  }

  import bbf-fiber-onu-emulated-mount {
     prefix onu;
  }

  import nokia-sdan-ber-tca-profiles-mounted {
    prefix nokia-sdan-ber-tca-prof-mounted;
  }

  import bbf-xponani-mounted {
    prefix bbf-xponani-mounted;
  }

  organization
    "Nokia";

  contact
     "Comments or questions about this Nokia YANG module should be
     directed to <mailto:isam.yang@nokia.com>.";


  description
     "This module contains a collection of YANG definitions for
     supporting Nokia specific requirements as applicable to its
     access network equipment.

     Specifically, this module augments the ANI interface
    with ber-tca-profile reference configuration.
         It also Augments the state data of ber-tca values
         to ANI interface

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

     revision 2022-06-16 {
        description
          "Initial revision";
        reference
          "Nokia specific. BBN-68509";
     }


  augment "/onu:onus/onu:onu/onu:root/if-mounted:interfaces/if-mounted:interface/bbf-xponani-mounted:ani" {
     description
       "Augment the ANI interface with NOKIA specific
        BER TCA SF/SD configuration parameters.";

     leaf ber-tca-profile-ref {
           type leafref {
              path "../../../../nokia-sdan-ber-tca-prof-mounted:ber-tca-profiles/"
                  + "nokia-sdan-ber-tca-prof-mounted:ber-tca-profile/"
                  + "nokia-sdan-ber-tca-prof-mounted:name";
           }
           description
               "Reference to  BER TCA configuration
                profile for SD/SF threshold.";
     }
  }
}
