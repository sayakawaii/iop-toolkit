module nokia-sdan-hardware-module-types-frommounted {
  yang-version 1.1;

  namespace "http://www.nokia.com/Fixed-Networks/BBA/yang/"
           + "nokia-sdan-hardware-module-types-frommounted";
    
  prefix nokia-sdan-hwmdlt-frommounted;

  organization
    "Nokia";
    
  contact
    "Comments or questions about this Nokia YANG module should be
     directed to <mailto:isam.mibsupport@nokia.com>.";
    
  description
    "This module contains a collection of YANG definitions for
     supporting Nokia specific requirements as applicable to its
     access network equipment.
    
     Specifically, this module contains a collection of YANG
     identities for pluggable hardware module type.
    
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.
    
     The product specifications and other technical or performance
     information contained herein are subject to change without
     notice. Updates of this document will be issued under the above
     NDA's.
    
     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
    
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
    
     Nokia reserves the right not to offer any or all of these
     products and to withdraw any or all of them at any future time.
    
     Copyright (C) 2021, Nokia. All Rights Reserved.";
    
    
  revision 2024-07-07 {
    description
      "Initial revision.";
    reference
      "Nokia specific EPIC BBN-107806";
  }
    
  identity eth-module-type-base {
    description
      "This identity is used as a base for type of the
       pluggable module.";
  }
    
  identity expected-eth-module-type-base {
    description
      "This identity is used as a base for expected type of the
       pluggable module.";
  }

  identity generic-optical {
    base eth-module-type-base;
    description
    "generic-optical includes any type of optical module.";
  }
     
  identity generic-electrical {
    base eth-module-type-base;
    description
      "generic-electrical includes any type of electrical module.";
  }
  
  identity optical-10g {
    base generic-optical;
    description
      "10G Optical module type. Corresponds to code 69 in
       ITU-T G.988 Table 9.1.5-1.";

  }
 
  identity optical-25g {
    base generic-optical;
    description
      "25G Optical module type. Corresponds to code 72 in
       MSA extension to ITU-T G.988 Table 9.1.5-1.";
  }

  identity electrical-10g {
    base generic-electrical;
    description
      "10G Electrical module type. Corresponds to code 49 in
       ITU-T G.988 Table 9.1.5-1.";
  }

  identity unrecognized {
    base eth-module-type-base;
    description
      "The type of module cannot be determined
       because the related item is not recognized.";
  }

  identity unequipped {
    base eth-module-type-base; 
    description
      "The type of module cannot be determined
       because the related item is not equipped.";
  }

  identity eth-generic-optical {
    base expected-eth-module-type-base;
    description
    "generic-optical includes any type of optical module.";
  }

  identity eth-generic-electrical {
    base expected-eth-module-type-base;
    description
      "generic-electrical includes any type of electrical module.";
  }

  identity eth-optical-10g {
    base eth-generic-optical;
    description
      "10G Optical module type. Corresponds to code 69 in
       ITU-T G.988 Table 9.1.5-1.";

  }

  identity eth-optical-25g {
    base eth-generic-optical;
    description
      "25G Optical module type. Corresponds to code 72 in
       MSA extension to ITU-T G.988 Table 9.1.5-1.";
  }

  identity eth-electrical-10g {
    base eth-generic-electrical;
    description
      "10G Electrical module type. Corresponds to code 49 in
       ITU-T G.988 Table 9.1.5-1.";
  }
}
