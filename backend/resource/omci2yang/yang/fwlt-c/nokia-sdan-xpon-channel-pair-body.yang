module nokia-sdan-xpon-channel-pair-body{
 yang-version 1.1;
 namespace "urn:broadband-forum-org:yang:nokia-sdan-xpon-channel-pair-body";

prefix nokia-sdan-xpon-channel-pair-body;

import bbf-xpon{
    prefix bbf-xpon;
}

import ietf-interfaces {
    prefix if;
  }

import nokia-sdan-xpon-types {
    prefix nokia-sdan-xpon-types;
}

import nokia-sdan-hspon-types {
    prefix nokia-sdan-hspon-types;
}

import bbf-xpon-types {
    prefix bbf-xpon-types;
}

organization
  "Nokia";

contact
  "Comments or questions about this Nokia YANG module should be
  directed to <mailto:isam.yang@nokia.com>.";

description
  "This specification is published by Nokia under Non-Disclosure
  Agreement(s) (NDA) with specific parties and has to be considered
  as Confidential Information as defined in such NDA. Nokia reserves
  the right to revise this document for any reason, including but
  not limited to conformity with standards promulgated by various
  agencies, utilization of advances in the state of the technical
  areas, or the reflection of changes in the design of any
  equipment, techniques, or procedures described or referred to
  herein.

  The product specifications and other technical or performance
  information contained herein are subject to change without notice.
  Updates of this document will be issued under the above NDA's.

  Nokia makes no representation or warranty, expressed or implied,
  with respect to the sufficiency, accuracy, or utility of any
  information or opinion contained herein. Nokia expressly advises
  that any use of for any purpose or reliance upon this technical
  reference is at the risk of the user and that Nokia shall not be
  liable for any damage or injury incurred by any person arising out
  of the sufficiency, accuracy, or utility of any information or
  opinion contained herein.

  This document is not to be construed as a suggestion to any
  manufacturer to modify or change any of its products, nor does
  this document represent any commitment by Nokia to sell or
  purchase any product. Nothing contained herein shall be construed
  as conferring by implication, estoppel, or otherwise any license
  or right under any patent, whether or not the use of any
  information herein necessarily employs an invention of any
  existing or later issued patent.

  Nokia reserves the right not to offer any or all of these products
  and to withdraw any or all of them at any future time.

  Copyright (C) 2022, Nokia. All Rights Reserved";

revision 2026-04-01 {
  description
    "remove ultra-low-latency-mode.";
  reference
    "TBD";
}


revision 2025-11-24 {
  description
    "add us-omci-granting.";
  reference
    "TBD";
}

revision 2024-04-15 {
  description
    "add Green DBA.";
  reference
    "TBD";
}

revision 2023-04-18 {
  description
    "update description of burst-overhead.";
  reference
    "TBD";
}

revision 2023-02-17 {
  description
    "add burst-overhead.";
  reference
    "TBD";
}

revision 2022-06-07 {
  description
    "add HSPON channel pair line rate.";
  reference
    "TBD";
}

revision 2022-03-09 {
  description
    "add Nokia under Non-Disclosure Agreement(s)";
  reference
    "TBD";
}

revision 2021-01-05 {
  description
    "Initial revision.";
  reference
    "TBD";
}

  augment '/if:interfaces/if:interface/bbf-xpon:channel-pair' {
   description "augmnet channel pair with ultra low latency mode";

   leaf twentyfivegs-channel-pair-line-rate {
      when "derived-from-or-self" +
           "(../bbf-xpon:channel-pair-type," +
           "'nokia-sdan-xpon-types:twentyfivegs')";

      type identityref {
      base "nokia-sdan-xpon-types:"+
           "twentyfivegs-channel-pair-line-rate-profile-base";
   }
      default
           "nokia-sdan-xpon-types:unplanned-25gs-cp-line-rate";
      description
           "Represents the planned downstream/upstream channel-pair
           speed for 25GS-PON.";
    }
    
    leaf hs-pon-channel-pair-line-rate {
      when "derived-from-or-self" +
           "(../bbf-xpon:channel-pair-type," +
           "'nokia-sdan-hspon-types:hs-pon')";
      type identityref {
        base "nokia-sdan-hspon-types:"+
             "hs-pon-channel-pair-line-rate-profile-base";
      }
      default
        "nokia-sdan-hspon-types:unplanned-hs-pon-cp-line-rate";
      description
        "Represents the planned downstream/upstream channel-pair
         speed for HS-PON.";
    }

    leaf burst-overhead {
      when
        "current()/../bbf-xpon:channel-pair-type = 'bbf-xpon-types:xgs'";
      type enumeration {
        enum "auto" {
          description
            "If burst overhead is configured to 'auto', the CAC will
             assume the worst-case and limit the configurable committed
             and assured services as such.
             Note that the inserted optical module might be capable of
             a lower PLOu, which DBA will use, but only best-effort
             services will be able to benefit from that in that case.";
        }
        enum "robust" {
          description
            "Robust PLOu size.";
        }
        enum "reduced" {
          description
            "Reduced PLOu size.
             Note that when 'reduced' is configured but the inserted
             optical module does not support it, an SFP mismatch alarm
             must be raised and the PON must stay down.
             If this is the case for one of the type-B channel-terminations,
             it will stay down and SWO is not possible.";
        }
      }
      default "auto";
      description
        "Represents the physical layer overhead (PLOu).
         The provisioned burst overhead is taken into account for service validation
         and remaining bandwidth calculation.";
    }

    leaf green-dba {
      type enumeration {
        enum "auto" {
          description
            "If Green DBA is configured to 'auto', the internal default
             in DBA will apply.";
        }
        enum "disabled" {
          description
            "Green DBA is disabled.";
        }
        enum "enabled" {
          description
             "Green DBA is enabled.";
         }
      }
      default "auto";
      description
        "Determines whether or not the Green DBA algorithm is used as DBA BW
         assignment algorithm in the uncongested case (the case in which the
         total upstream BW demand is smaller than the available upstream BW
         for the PON).";
    }

    leaf us-omci-granting {
      type enumeration {
        enum "conservative" {
          description
            "Any ONU on this channel-pair will get a chance to send upstream
             OMCI traffic at least once every 1ms. This setting foresees generous
             upstream bandwidth and optimized latency for the management-related
             communication between the OLT and the ONUs.";
        }
        enum "relaxed" {
          description
            "Any ONU on this channel-pair will get a chance to send upstream
             OMCI traffic once every 4ms. This setting provides more optimized
             bandwidth with less stringent latency for the management-related
             communication between the OLT and the ONUs.";
        }
      }
      default "conservative";
      description
        "This channel-pair level attribute modifies the frequency at which
         the OLT channel-pair will allocate grants to the ONUs for their OMCI
         communication. It therefore influences the amount of management
         overhead on the channel-pair in the upstream direction (less bandwidth
         reserved for OMCI means more useful bandwidth for user traffic, which
         can have a significant effect in a large-scale scenario). The channel-pair
         interfaces supporting the 'relaxed' behaviour are XGS-PON, 25GS-PON and
         50G-PON interfaces. A modification of this attribute on GPON channel-pair
         interfaces (any product) and on XGS-PON channel-pair interfaces on legacy
         products (see product-specific documentation) will be accepted but silently
         ignored, so it won't have any effect. For products supporting both 'relaxed'
         and 'conservative' options, a modification of this attribute will only be
         permitted when there is enough upstream PON capacity available on the
         corresponding channel-pair interface.";
    }

  }
}
