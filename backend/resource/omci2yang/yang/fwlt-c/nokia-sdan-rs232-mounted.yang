module nokia-sdan-rs232-mounted {
  yang-version 1.1;
  namespace "http://www.nokia.com/Fixed-Networks/BBA/yang/"
             + "nokia-sdan-rs232-mounted";
  prefix nokia-rs232-mounted;
 
  import nokia-sdan-ip-l4-binding-common-mounted {
    prefix nokia-sdan-ip-l4-bind-mounted;
  }
 
  import iana-if-type-mounted {
    prefix ianaift-mounted;
  }
 
  import ietf-interfaces-mounted {
    prefix if-mounted;
  }
 
  import bbf-fiber-onu-emulated-mount {
     prefix onu;
  }
 
  import nokia-sdan-ssh-server-mounted {
    prefix nokia-sdan-ssh-server-mounted;
  }
 
  organization
    "Nokia";
 
  contact
    "Comments or questions about this Broadband Forum YANG module
     should be directed to <mailto:isam.yang@nokia.com>.";
 
 
  description
    "This module contains a collection of YANG definitions for
     Physical path termination point RS232 UNI.
 
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.
 
     The product specifications and other technical or performance
     information contained herein are subject to change without
     notice. Updates of this document will be issued under the above
     NDA's.
 
     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
 
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
 
     Nokia reserves the right not to offer any or all of these
     products and to withdraw any or all of them at any future time.
 
     Copyright (C) 2022, Nokia. All Rights Reserved.";
 
  revision 2026-03-25 {
    description
      "Initial revision.";
    reference
      "";
  }
 
  grouping rs232-port-config {
    description
      "Grouping of RS232 serial port configuration parameters.
       Based on ITU-T G.988 9.15.1 Physical path termination point RS232 UNI.";
 
    leaf port-mode {
      type enumeration {
        enum half-duplex { value 0; description "Half duplex mode"; }
        enum full-duplex { value 1; description "Full duplex mode"; }
      }
      description
        "RS232 controller chip working mode";
    }
 
    leaf baud-rate {
      type enumeration {
        enum baud-300 { value 0; description "300 bit/s"; }
        enum baud-600 { value 1; description "600 bit/s"; }
        enum baud-1200 { value 2; description "1200 bit/s"; }
        enum baud-2400 { value 3; description "2400 bit/s"; }
        enum baud-4800 { value 4; description "4800 bit/s"; }
        enum baud-9600 { value 5; description "9600 bit/s"; }
        enum baud-19200 { value 6; description "19200 bit/s"; }
        enum baud-38400 { value 7; description "38400 bit/s"; }
        enum baud-43000 { value 8; description "43000 bit/s"; }
        enum baud-56000 { value 9; description "56000 bit/s"; }
        enum baud-57600 { value 10; description "57600 bit/s"; }
        enum baud-115200 { value 11; description "115200 bit/s"; }
      }
      description
        "RS232 port baud rate (ITU-T G.988 9.15.1)";
    }
 
    leaf data-bits {
      type uint8 {
        range 5..8;
      }
      description
        "Number of data bits (5/6/7/8)";
    }
 
    leaf parity {
      type enumeration {
        enum no-parity { value 0; description "No parity check"; }
        enum odd-parity { value 1; description "Odd parity"; }
        enum even-parity { value 2; description "Even parity"; }
      }
      description
        "Data parity check mode";
    }
 
    leaf stop-bits {
      type uint8 {
        range 1..2;
      }
      description
        "Number of stop bits (1/2)";
    }
 
    leaf flow-control {
      type enumeration {
        enum no-flow-control { value 0; description "No flow control"; }
        enum hardware-flow-control { value 1; description "RTS/CTS"; }
        enum software-flow-control { value 2; description "Xon/Xoff"; }
      }
      description
        "Data flow control mode";
    }
  }
 
  augment "/onu:onus/onu:onu/onu:root/if-mounted:interfaces/if-mounted:interface" {
    when "derived-from-or-self(if-mounted:type,
          'ianaift-mounted:rs232')";
    description
      "Augments config nodes for RS232 UNI.";
 
    container rs232 {
      presence "rs232";
      description
        "Configuration nodes for an RS232 capable ONT.";
 
      uses nokia-sdan-ip-l4-bind-mounted:transport-config {
        refine "local-port" {
          mandatory true;
        }
        refine "protocol" {
          mandatory true;
        }
      }
	  
      leaf ip-host-ref {
        type leafref {
          path '../../../../if-mounted:interfaces/if-mounted:interface/if-mounted:name';
        }
        mandatory true;
        description
          "Reference to the IP host configuration.
           Maps to TCP/UDP Config Data ME attr 'IP host config pointer'
           which points to IP Host Config Data ME (134) or IPv6 Host Config Data ME (347).";
      }
	  
      leaf ssh-server-ref {
        type leafref {
          path "../../../../nokia-sdan-ssh-server-mounted:ssh-server/" +
               "nokia-sdan-ssh-server-mounted:name";
        }
        description
          "Reference to an SSH server instance (by name) under the ONU root.";
      }
 
      uses rs232-port-config;
    }
  }
   
  augment "/onu:onus/onu:onu/onu:root/if-mounted:interfaces-state/if-mounted:interface" {
    when "derived-from-or-self(if-mounted:type,
          'ianaift-mounted:rs232')";
    description
      "Augments operational state nodes for RS232 UNI.";
 
    container rs232 {
      description
        "The status node for RS232 capable ONT.";
      reference
        "ITU-T G.988 9.15.1 Physical path termination point RS232 UNI.";
      leaf min-send-payload {
        type uint32;
        description
          "Fixed-length mode serial data acquisition length (4 bytes)";
      }
 
      leaf min-send-time {
        type uint32;
        description
          "Timing mode serial data acquisition time (4 bytes)";
      }
    }
  }
}
