module nokia-bbf-vlan-sub-interface-vector-icmpv6-l2fwd-fiber-pon-dev {

  namespace "http://www.nokia.com/Fixed-Networks/BBA/yang/" +
            "nokia-bbf-vlan-sub-interface-vector-icmpv6-l2fwd-fiber-pon-dev";

  prefix nokia-bbf-vlan-sub-interface-vector-icmpv6-l2fwd-fiber-pon-dev;


  import bbf-vlan-sub-interface-vector {
        prefix bbf-vsi-vctr;
  }

   import bbf-vlan-sub-interface-vector-usage {
    prefix bbf-vsi-vctr-usg;
  }

  import bbf-vlan-sub-interface-vector-icmpv6 {
    prefix bbf-vsi-vctr-icmpv6;
  }

  organization
    "Nokia";

  contact
    "isam.yang@nokia.com";

  description
    "This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2022-02-18 {
    description
      "Initial revision.";
    reference
      "Nokia specific";
  }

  deviation "/bbf-vsi-vctr:vsi-vector-profiles/bbf-vsi-vctr:vsi-vector-profile/bbf-vsi-vctr-icmpv6:icmpv6" {
     deviate add {
      must "current()/../bbf-vsi-vctr-usg:interface-usage/bbf-vsi-vctr-usg:interface-usage = 'user-port' "
          {
        error-message "interface-usage of vector profile for icmpv6 must be user-port";
      }

    }

  }

}
