module nokia-sdan-if-xpon-aug-common-dev {

  namespace "http://www.nokia.com/Fixed-Networks/BBA/yang/"
    + "nokia-sdan-if-xpon-aug-common-dev";

  prefix nokia-sdan-if-xpon-aug-common-dev;


  import ietf-interfaces {
    prefix if;
  }

  import bbf-xpon{
    prefix bbf-xpon;
  }

  import nokia-sdan-if-xpon-aug {
    prefix nokia-sdan-if-xpon-aug;
  }

  import bbf-xpon-types {
    prefix bbf-xpon-types;
  }

  import nokia-sdan-xpon-types {
    prefix nokia-sdan-xpon-types;
  }
  
  import nokia-sdan-hspon-types {
    prefix nokia-sdan-hspon-types;
  }

  import nokia-ber-tca-profiles {
     prefix nokia-ber-tca-prof;
  }

  organization
    "Nokia";

  contact
    "isam.yang@nokia.com";

  description
    "This specification is published by Nokia under Non-Disclosure
  Agreement(s) (NDA) with specific parties and has to be considered
  as Confidential Information as defined in such NDA. Nokia reserves
  the right to revise this document for any reason, including but
  not limited to conformity with standards promulgated by various
  agencies, utilization of advances in the state of the technical
  areas, or the reflection of changes in the design of any
  equipment, techniques, or procedures described or referred to
  herein.

  The product specifications and other technical or performance
  information contained herein are subject to change without notice.
  Updates of this document will be issued under the above NDA's.

  Nokia makes no representation or warranty, expressed or implied,
  with respect to the sufficiency, accuracy, or utility of any
  information or opinion contained herein. Nokia expressly advises
  that any use of for any purpose or reliance upon this technical
  reference is at the risk of the user and that Nokia shall not be
  liable for any damage or injury incurred by any person arising out
  of the sufficiency, accuracy, or utility of any information or
  opinion contained herein.

  This document is not to be construed as a suggestion to any
  manufacturer to modify or change any of its products, nor does
  this document represent any commitment by Nokia to sell or
  purchase any product. Nothing contained herein shall be construed
  as conferring by implication, estoppel, or otherwise any license
  or right under any patent, whether or not the use of any
  information herein necessarily employs an invention of any
  existing or later issued patent.

  Nokia reserves the right not to offer any or all of these products
  and to withdraw any or all of them at any future time.

  Copyright (C) 2022, Nokia. All Rights Reserved"; 

  revision 2024-08-24 {
    description
      "remove xgpon deviations and
       correct the error message.";
    reference
      "Nokia Specific.";
  }

  revision 2023-02-24 {
    description
      "add some deviations.";
    reference
      "Nokia Specific.";
  }

  revision 2023-02-06 {
    description
      "Initial revision.";
    reference
      "Nokia Specific.";
  }

  deviation "/if:interfaces/if:interface/bbf-xpon:channel-termination/nokia-sdan-if-xpon-aug:channel-termination-type-b-pon-location-data/nokia-sdan-if-xpon-aug:pon-id-type/nokia-sdan-if-xpon-aug:ngpon2-ptp/nokia-sdan-if-xpon-aug:ngpon2-ptp-admin-label" {
    description "This parameter is not supported.";
    deviate not-supported;
  }

  deviation "/if:interfaces/if:interface/bbf-xpon:channel-termination/nokia-sdan-if-xpon-aug:channel-termination-type-b-pon-location-data/nokia-sdan-if-xpon-aug:slot-id" {
    deviate add {
      must "not(boolean(current())) or " 
          +"(current()/../../bbf-xpon:meant-for-type-b-primary-role = 'false')"
      {
        error-message "This parameter slot-id can only be set on secondary channel-termination.";
      }
    }
  }

 deviation "/if:interfaces/if:interface/bbf-xpon:channel-termination/nokia-sdan-if-xpon-aug:channel-termination-type-b-pon-location-data/nokia-sdan-if-xpon-aug:port-id" {
    deviate add {
      must "not(boolean(current())) or " 
          +"(current()/../../bbf-xpon:meant-for-type-b-primary-role = 'false')"
      {
        error-message "This parameter port-id can only be set on secondary channel-termination.";
      }
    }
  }
  
  deviation "/if:interfaces/if:interface/bbf-xpon:channel-termination/nokia-sdan-if-xpon-aug:channel-termination-type-b-pon-location-data/nokia-sdan-if-xpon-aug:access-node-id" {
    deviate add {
      must "not(boolean(current())) or " 
          +"(current()/../../bbf-xpon:meant-for-type-b-primary-role = 'false')"
      {
        error-message "This parameter access-node-id can only be set on secondary channel-termination.";
      }
    }
  }

  deviation "/if:interfaces/if:interface/bbf-xpon:channel-termination/nokia-sdan-if-xpon-aug:laser-on-by-default" {
    deviate add {
      must "current() = 'true' or "
         + "((current()/../bbf-xpon:channel-termination-type != 'bbf-xpon-types:ngpon2-twdm') and"
         + "(current()/../bbf-xpon:channel-termination-type != 'nokia-sdan-xpon-types:twentyfivegs') and"
         + "(current()/../bbf-xpon:channel-termination-type != 'nokia-sdan-hspon-types:hs-pon'))" {
        error-message "The laser-on-by-default must be true for NGPON2/25GS.";
      }
    }
  }

  deviation "/if:interfaces/if:interface/bbf-xpon:channel-pair/nokia-sdan-if-xpon-aug:ber-tca-profile" {
    deviate add {
      must "current()/../bbf-xpon:channel-pair-type != 'bbf-xpon-types:gpon' or "
      + "(/nokia-ber-tca-prof:ber-tca-profiles/nokia-ber-tca-prof:ber-tca-profile[nokia-ber-tca-prof:name = current()]/nokia-ber-tca-prof:sd-threshold >= 4 and"
      + "/nokia-ber-tca-prof:ber-tca-profiles/nokia-ber-tca-prof:ber-tca-profile[nokia-ber-tca-prof:name = current()]/nokia-ber-tca-prof:sd-threshold <= 9)" {
        error-message "The sd-threshold should be 4~9 for GPON.";
      }
    }
  }
 
  deviation "/if:interfaces/if:interface/bbf-xpon:channel-termination/nokia-sdan-if-xpon-aug:laser-on-by-default" {
    deviate add {
      must "current() = 'false' or"
         +"(not(boolean(current()/../bbf-xpon:meant-for-type-b-primary-role)))"
      {
        error-message "The meant-for-type-b-primary-role can only be set when laser-on-by-default is false.";
      }
    }
  }

}
