module nokia-interfaces-statistics {
  yang-version 1.1;
  namespace "http://www.nokia.com/Fixed-Networks/BBA/yang/"
          + "nokia-interfaces-statistics";

  prefix nokia-itfstat;

  import ietf-interfaces {
    prefix if;
  }

  import ietf-yang-types {
    prefix yang;
  }

  organization
    "Nokia";

  contact
    "Comments or questions about this Nokia YANG module should be 
     directed to <mailto:isam.yang@nokia.com>.";

  description
    "This module contains a collection of YANG definitions for 
     supporting Nokia specific requirements as applicable to its 
     access network equipment.
     
     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2018, Nokia. All Rights Reserved.";

  revision 2024-03-06 {
    description
      "dropped-bytes leafs support for inbound and outbound packets
       added for rolling statistics";
    reference
      "Nokia specific";
  }

  revision 2018-10-25 {
    description
      "Initial revision.";
    reference
      "Nokia specific"; 
  }

  feature nokia-total-pkts {
    description
      "Indicates support for total packets received, transmitted
       on the interface. This also includes support for dropped
       packets counters.";
  }

  augment '/if:interfaces/if:interface' {
    description
      "Data nodes for the statistics configuration parameters.";

    container statistics {
      description
        "A collection of interface-related statistics objects.";

      leaf enable {
        type enumeration {
          enum best-effort {
            description
              "Enables the collection of interface statistics that are
               defined in /interfaces-state/interface/statistics 
               according:
               - the applicability of the counters for the interface 
                 type. 
                 E.g. an interface of the type fastdsl does not have
                 packet counters. Configuring best-effort mode is
                 accepted but packet counters are still not available.
               - the support of the counters for the interface 
                 instance itself. 
                 E.g. the position of the interface as a user or as a 
                 network interface might affect the availability of 
                 counters. Configuring best-effort mode on particular 
                 interface instances can be accepted but still no 
                 counters might be available.

               Summarized, the 'best-effort' mode provides all the 
               counters that are available from the moment the 
               interface is up and running.";
          }
          enum false {
            description
              "No counters are to be collected for this interface.";
          }
          enum all-available {
            description
              "Enables the collection of interface statistics that are
               defined in interfaces-state/interface/statistics but 
               are subject to dimensioning constraints. I.e. a system 
               might support some counters but might not support them 
               simultaneously on all interfaces.
               
               In 'best-effort' mode such counters are not provided. 
               
               In 'all-available' mode the system does provide these 
               counters. Setting this mode allows the management 
               system to control on which interfaces these counters 
               shall be collected. This configuration is rejected if 
               the system's dimensioning constraint is reached.";
          }
        }
        default "best-effort";
	
        description
          "Affects the collection of statistics and making them 
           available through /interfaces-state/interface/statistics.";
      }
    }
  }

  augment '/if:interfaces-state/if:interface/if:statistics' {
    description
      "Total drop bytes counter for interfaces.";

    leaf in-dropped-bytes{
      if-feature "nokia-itfstat:nokia-total-pkts";
      type yang:counter64;
      description
        "The number of inbound bytes that were dropped on the
        interface, e.g. due to errors or lack of buffer space.";
    }

    leaf out-dropped-bytes{
      if-feature "nokia-itfstat:nokia-total-pkts";
      type yang:counter64;
      description
        "The number of outbound bytes that could not be
        transmitted on the interface, e.g. due to errors or
        lack of buffer space.";
    }
  }
}
