module nokia-sdan-802-dot1x-ext-dynamic-authorization {
  yang-version 1.1;
  namespace "http://www.nokia.com/Fixed-Networks/BBA/yang/"
          + "nokia-sdan-802-dot1x-ext-dynamic-authorization";
  prefix "nokia-dyn-auth-ext";

  import ietf-interfaces {
    prefix "if";
  }
  import ieee802-dot1x {
    prefix "dot1x";
  }
  import nokia-802-dot1x-ext {
    prefix "nokia-dot1x-ext";
  }
  import bbf-yang-types {
    prefix "bbf-yang";
  }
  import ietf-inet-types {
    prefix "inet";
  }
  import nokia-sdan-radius-dynamic-authorization-types {
    prefix "nokia-dyn-auth-types";
  }
  import nokia-yang-types {
    prefix nok-typ;
  }

  organization
    "Nokia";

  contact
    "Comments or questions about this Nokia YANG module should be
     directed to <mailto:isam.yang@nokia.com>.";

  description
    "This module contains a collection of YANG definitions for
     supporting Nokia specific requirements as applicable to its
     access network equipment.

     Specifically, this module augments the standard IEEE 802.1X model
     with configuration and state data for the dynamic authorization
     feature.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

  revision 2024-11-20 {
    description
      "Commets Addressal.";
    reference
      "Nokia specific";
  }

  revision 2024-06-12 {
    description
      "Introduced configuration and state YANG support for Dynamic
       Authorization requests handling from the RADIUS server (or)
       from the Dynamic Authorization Client(DAC).";
    reference
      "Nokia specific";
  }

  grouping user-vsi-info {
    description
      "The user vlan-sub-interface information";
    leaf user-vsi-name {
      type string;
      description
        "The user vlan-sub-interface for which dynamic associations
        were received from the RADIUS server (or) Dynamic
        Authorization Client(DAC).";
    }
  }

  grouping dyn-assoc-received-source {
    description
      "The source IP address of the Dynamic Authorization Client(DAC)
      (or) RADIUS server from which the Dynamic Authorization
      parameters are received.";
    leaf dyn-assoc-source {
      type inet:ip-address;
      description
        "IPv4 or IPv6 address of the RADIUS server (or) Dynamic
        Authorization Client(DAC).";
    }
  }

  grouping dyn-assoc-origin {
    description
      "The origin of the dynamic association parameter that were
       received";
    leaf assoc-origin {
      type identityref {
        base nokia-dyn-auth-types:dyn-assoc-origin-base;
      }
      description
        "Indicates the origin of dynamic association request.
        Either via Change of Authorization(CoA) from the Dynamic
        Authorization Client(DAC) (or) via access-accept from the
        RADIUS server as part of the RADIUS 802.1X user
        authentication.";
    }
  }

  grouping vsi-qos-dyn-association-info {
    description
      "VSI attachment to the QoS policy profile association data";
    leaf profile-name {
      type bbf-yang:string-ascii64;
      description
        "The QoS policy profile name received from the RADIUS server
        (or) Dynamic Authorization Client(DAC).";
    }
    uses nokia-dyn-auth-ext:dyn-assoc-origin;
    uses nokia-dyn-auth-ext:dyn-assoc-received-source;
  }

  grouping vsi-forwarder-dyn-association-info {
    description
      "VSI to the forwarder dynamic association data";
    leaf forwarder-name {
      type nok-typ:nokia-string-ascii100;
      description
        "The 'forwarder' name received from the RADIUS server (or)
        Dynamic Authorization Client(DAC)";
    }
    uses nokia-dyn-auth-ext:dyn-assoc-origin;
    uses nokia-dyn-auth-ext:dyn-assoc-received-source;
  }

  grouping vsi-dynamic-assoc-parameters {
    description
      "VSI dynamic association data";
    uses nokia-dyn-auth-ext:user-vsi-info;
    container vsi-forwarder-association {
      presence
        "The presence of this container indicates the presence of
        forwarder for the dynamic association to the VSI";

      description
        "VSI to the forwarder dynamic association data";
      uses nokia-dyn-auth-ext:vsi-forwarder-dyn-association-info;
    }
    container vsi-ingress-qos-association {
      presence
        "The presence of this container indicates the presence of
        ingress QoS policy profile for the dynamic association to
        the VSI";
      description
        "Dynamic association of the ingress QoS Policy profile to
        the VSI";
      uses nokia-dyn-auth-ext:vsi-qos-dyn-association-info {
        refine "profile-name" {
          description
            "The ingress QoS policy profile name received from the
            RADIUS server (or) Dynamic Authorization client(DAC).";
        }
      }
    }
    container vsi-egress-qos-association {
      presence
        "The presence of this container indicates the presence of
        egress QoS policy profile for the dynamic association to
        the VSI";
      description
        "Dynamic association of the egress QoS Policy profile to
        the VSI";
      uses nokia-dyn-auth-ext:vsi-qos-dyn-association-info {
        refine profile-name {
          description
            "The egress QoS policy profile name received from the
            RADIUS server (or) Dynamic Authorization client(DAC).";
        }
      }
    }
  }

  grouping assoc-failure-reason-details {
    description
      "Dynamic association failure reason and additional details.";
    leaf reason {
      type identityref {
        base "nokia-dyn-auth-types:"
             +"dyn-assoc-attach-failure-reason-base";
      }
      description
        "Reason for the dynamic assocation parameters apply failure.";
    }
    leaf failure-details {
      type string;
      description
        "Additional details about the failure.
        For example, if incase the dynamic association failure because
        of system restrictions then this leaf will have additional
        details about the system restriction.";
    }
  }

  grouping vsi-dynamic-assoc-info {
    description
      "VSI dynamic association data which were received from the
      RADIUS server (or) Dynamic Authorization Client(DAC)";
    list vsi-dynamic-assoc-data {
      key "user-vsi-name";
      description
        "VSI dynamic association data";
      uses nokia-dyn-auth-ext:vsi-dynamic-assoc-parameters;
    }

    notification vsi-dynamic-assoc-removed {
      description
        "Notification to indicate the dynamically associated
        parameters which were applied as part of the RADIUS 802.1X
        user authentication or as part of the dynamic CoA request
        from Dynamic Authorization Client (DAC) - have been removed.
        Example scenarios include:
        disabling dynamic authorization control on a vENET interface,
        disabling dynamic forwarder association on a VSI,
        disabling dynamic QoS association on a VSI, or
        RADIUS user authentication session logoff from a Supplicant.";

      uses nokia-dyn-auth-ext:vsi-dynamic-assoc-parameters;
      leaf reason {
        type identityref {
          base nokia-dyn-auth-types:dyn-assoc-removal-reason-base;
        }
        description
          "Reason for the dynamically associated parameters
           removal.";
      }
    }

    notification vsi-dynamic-association-failure {
      description
        "Notification to indicate VSI dynamic association
        request failure.";
      uses nokia-dyn-auth-ext:user-vsi-info;
      container forwarder {
        presence
          "The presence of this container indicates the data available
          for the forwarder";
        description
          "Dynamic association failure details of the forwarder";
        uses nokia-dyn-auth-ext:vsi-forwarder-dyn-association-info;
        uses nokia-dyn-auth-ext:assoc-failure-reason-details;
      }
      container ingress-qos {
        presence
          "The presence of this container indicates the data available
          for the QoS policy profile which intented to be attached as
          ingress";
        description
          "Dynamic association failure details of the ingress QoS
          profile";
        uses nokia-dyn-auth-ext:vsi-qos-dyn-association-info {
          refine "profile-name" {
            description
              "The ingress QoS policy profile name received from the
              RADIUS server (or) Dynamic Authorization client(DAC).";
          }
        }
        uses nokia-dyn-auth-ext:assoc-failure-reason-details;
      }
      container egress-qos {
        presence
          "The presence of this container indicates the data available
          for QoS policy profile which intented to be attached as
          egress";
        description
          "Dynamic association failure details of the egress
          QoS profile";
        uses nokia-dyn-auth-ext:vsi-qos-dyn-association-info {
          refine "profile-name" {
            description
              "The egress QoS policy profile name received from the
              RADIUS server (or) Dynamic Authorization client(DAC).";
          }
        }
        uses nokia-dyn-auth-ext:assoc-failure-reason-details;
      }
    }
  }

  grouping authenticator-session-id {
    description
      "The session ID of the authenticator";
    leaf session-id {
      type bbf-yang:string-ascii64;
      description
        "The session ID of the authenticator";
    }
  }

  grouping port-bounce-failure-info {
    description
      "The port-bounce failure reasons";
      notification dynamic-authorization-port-bounce-failure
      {
        description
          "Notification to indicate port-bounce request failure.";
        leaf reason {
        type identityref {
          base "nokia-dyn-auth-types:"
            +"port-bounce-failure-reason-base";
        }
        description
          "Reason for the port-bounce failure.";
        }
        leaf failure-details {
          type nok-typ:nokia-string-ascii100;
          description
            "Additional details about the failure.";
        }
     }
  }

  augment "/if:interfaces/if:interface/dot1x:pae" {
    description
      "Extends the configuration of the 802.1X PAE with the
       Dynamic Authorization support.";

    container dynamic-auth {
      presence
        "The presence of this container enables Dynamic
         Authorization.";
      description
        "The configuration support for enabling Dynamic Authorization
         feature";
      leaf dynamic-auth-control {
        type identityref {
          base nokia-dyn-auth-types:dynamic-auth-enable-control-base;
        }

        default nokia-dyn-auth-types:dynamic-auth-enable-coa-and-dm;
        description
          "Determines the control for Dynamic Authorization requests
           processing.Change of Authorization(CoA) and Disconnect
           Message(DM) features.";
        reference
          "RFC 5176";
      }
    }
  }

  augment "/if:interfaces-state/if:interface/nokia-dot1x-ext:pae/"
    +"nokia-dot1x-ext:mac/nokia-dot1x-ext:session" {
    description
      "Extends the state data of the 802.1X PAE
       mac or mab based session with the dynamic CoA data and the
       session ID of the authenticator.";
    uses nokia-dyn-auth-ext:authenticator-session-id;
    uses nokia-dyn-auth-ext:vsi-dynamic-assoc-info;
    uses nokia-dyn-auth-ext:port-bounce-failure-info;
  }

}
