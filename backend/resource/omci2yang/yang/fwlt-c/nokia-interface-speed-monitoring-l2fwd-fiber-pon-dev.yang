module nokia-interface-speed-monitoring-l2fwd-fiber-pon-dev {
  
  namespace "http://www.nokia.com/Fixed-Networks/BBA/yang/" +
            "nokia-interface-speed-monitoring-l2fwd-fiber-pon-dev";

  prefix nokia-interface-speed-monitoring-l2fwd-fiber-pon-dev;
  

  import nokia-interface-speed-monitoring {
    prefix nokia-itf-tm;
  }

  import ietf-interfaces {
    prefix if;
  }

  import iana-if-type {
    prefix ianaift;
  }

  import bbf-xpon-if-type {
    prefix bbf-xponift;
  }

  organization
    "Nokia";

  contact
    "isam.yang@nokia.com";

  description
    "This module contains a collection of YANG deviations on top
     of standard for supporting l2fwd YANG module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2017-2018, Nokia. All Rights Reserved.";


  revision 2023-08-27 {
    description
      "Extend speed monitoring support for vani interface.";
    reference
      "Nokia specific";
  }

  revision 2021-11-05 {
    description
      "Initial revision.";
    reference
      "Nokia specific";
  }

  deviation "/if:interfaces/if:interface/nokia-itf-tm:speed-monitoring/nokia-itf-tm:enable" {
    deviate add{
      must "(current() = 'false') or"
          + "(current()/../../if:type ='bbf-xponift:channel-termination') or (current()/../../if:type ='ianaift:ethernetCsmacd') or (current()/../../if:type ='bbf-xponift:v-ani')"{
           error-message "Speed monitoring Cannot Enable on this interface";
      }
    }
  }

  deviation "/nokia-itf-tm:interface-speed-monitoring/nokia-itf-tm:period-length" {
    deviate add {
      max-elements 1;
    }

    deviate replace {
      type enumeration {
        enum 5-seconds {
          value 0;
          description
            "A period of 5 seconds.";
        }
        enum 1-minute {
          value 1;
          description
            "A period of 1 minute.";
        }
        enum 30-seconds {
          value 3;
          description
            "A period of 30 seconds.";
        }
        enum 5-minutes {
          value 4;
          description
            "A period of 5 minutes.";
        }
        enum 15-minutes {
          value 5;
          description
            "A period of 15 minutes.";
        }
      }
    }
  }
}
