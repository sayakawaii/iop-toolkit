module nokia-hardware-disk-resource {
  yang-version 1.1;
  namespace "http://www.nokia.com/Fixed-Networks/BBA/yang/"
          + "nokia-hardware-disk-resource";

  prefix nokia-disk;

  import iana-hardware {
    prefix ianahw;
  }

  import ietf-hardware {
    prefix hw;
  }

  organization
    "Nokia";

  contact
    "Comments or questions about this Nokia YANG module should be
     directed to <mailto:isam.yang@nokia.com>.";

  description
    "This module contains a collection of YANG definitions for
     supporting Nokia specific requirements as applicable to its
     access network equipment.

     Specifically, this module models data to manage the non volatile memory.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2019, Nokia. All Rights Reserved.";

  revision 2019-09-06 {
    description
      "Initial revision.";
    reference
      "Nokia specific";
  }

  augment "/hw:hardware-state/hw:component" {
    when "derived-from-or-self (hw:class, 'ianahw:storage-drive')";

    description
      "Data nodes for hard drives of identity class 'storage-drive'.";

    container nand-resource-data {
      config false;
      description
        "Container containing nand specific resource data.";

      leaf max-erase-cycles {
         type uint64;
         description
           "The maximum number times one sectory has been erased.
            This number can increase slowly over time, a high
            increasing number might lead to damage on the NAND storage.";
      }
      leaf bad-sectors {
         type uint64;
         description
           "The number of bad, or unusable, sectors.
            This number can increase slowly over time, a high
            increasing number might lead to damage on the NAND storage.";
      }
    }

    container volume-resource-data {
      description
        "volumes container";

      list volume-resource-list {
        key name;
        description "volume resource list";
        
        leaf name {
          type string;
          description
            "The name of the volume or partition.";
            
        }
        leaf size {
           type uint64;
           units "Kilobytes";
           description
             "The total size of this volume or partition.";
        }
        leaf free {
           type uint64;
           units "Kilobytes";
           description
             "The amount of free size of volume or partition.";
        }
      }
    }
  }
}
