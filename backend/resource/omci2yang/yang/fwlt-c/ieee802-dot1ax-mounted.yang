module ieee802-dot1ax-mounted {
  yang-version 1.1;
  namespace "urn:ieee:std:802.1AX:yang:ieee802-dot1ax-mounted";
  prefix "dot1ax-mounted";

  import bbf-fiber-onu-emulated-mount {
     prefix onu;
  }
  import ietf-interfaces-mounted { prefix "if-mounted"; }
  import iana-if-type-mounted { prefix "ianaift-mounted"; }

  organization
    "Institute of Electrical and Electronics Engineers";

  contact
  	"WG-URL: http://grouper.ieee.org/groups/802/1/
    WG-EMail: stds-802-1@ieee.org

    Contact: IEEE 802.1 Working Group Chair
    Postal: C/O IEEE 802.1 Working Group
            IEEE Standards Association
            445 Hoes Lane
            P.O. Box 1331
            Piscataway
            NJ 08855-1331
            USA
 	
    E-mail: STDS-802-1-L@LISTSERV.IEEE.ORG";

  description
    "Link Aggregation allows one or more links to be aggregated
    together to form a Link Aggregation Group, such that a Media
    Access Control (MAC) Client can treat the Link Aggregation Group
    as if it were a single link. To this end, it specifies the
    establishment of data terminal equipment (DTE) to DTE logical
    links, consisting of N parallel instances of full duplex
    point-to-point links operating at the same data rate.";

  revision "2026-01-21" {
    description
      "Initial Version.";
    reference
      "IEEE 802.1AX-2008, Link Aggregation.";
  }

  // ---------------------------------------------------
  // Configuration objects used by 802.1AX YANG module
  // ---------------------------------------------------


  //
  //  Aggregator Nodes
  //
  augment "/onu:onus/onu:onu/onu:root/if-mounted:interfaces/if-mounted:interface" {
    when "if-mounted:type = 'ianaift-mounted:ieee8023adLag'" {
      description
        "Applies to Ethernet interfaces or Bridge Ports.";
      }
    description
      "Augment Interface with Aggregator configuration attributes.";
    container aggregator {
      presence
        "Presence of this container.";
      description
        "Contains the Aggregator configuration information which
        provides the management controls necessary to allow an
        instance of an Aggregator to be managed.";

      leaf name {
        type string {
          length "0..255";
        }
        description
          "A human-readable text string containing a locally
          significant name for the Aggregator";
        reference
          "IEEE 802.1AX-2008, Clause 6.3.1.1.3";
      }

      leaf primary-lag-port-ref {
        type leafref { path '../../../../if-mounted:interfaces/if-mounted:interface/if-mounted:name'; }

        must "(../../../../if-mounted:interfaces/if-mounted:interface[if-mounted:name=current()]/dot1ax-mounted:aggregation-port"
             +"/dot1ax-mounted:aggregation-port-lacp/dot1ax-mounted:actor-admin-key = current()"
             +"/../dot1ax-mounted:aggregator-lacp/dot1ax-mounted:actor-admin-key)"
        {
            error-message "Primary LAG port is a reference to a ethernet"
                        + "interface which should be a member port of LAG.";
        }
        mandatory true;
        description
        "Primary LAG port is a reference to an ethernet interface which
         is a member port of LAG. This port reference shall be used as reference
         for protocol handling whenever a packet needs to be manipulated.";
      }

      container aggregator-lacp {
        description
          "Contains aggregator LACP operational data.";
        leaf actor-admin-key {
          type int16;
          description
            "The current administrative value of the Key for the
            Aggregator. The administrative Key value may differ
            from the operational Key value for the reasons
            discussed in 5.6.2. The meaning of particular Key
            values is of local significance.";
          reference
            "IEEE 802.1AX-2008, Clause 6.3.1.1.7";
        }
      } // aggregator-lacp
    } // aggregator
  } // augment if:interface


  //---------------------------------------------------
  //  Aggregation Port Nodes
  //---------------------------------------------------
  augment "/onu:onus/onu:onu/onu:root/if-mounted:interfaces/if-mounted:interface" {
    when "if-mounted:type = 'ianaift-mounted:ethernetCsmacd'" {
      description
        "Applies to Ethernet interfaces or Bridge Ports.";
      }
    description
      "Augment interface model with Aggregation port
      configuration nodes.";
    reference
      "IEEE 802.1AX-2008, Clause 6.3.2";
    container aggregation-port {
      presence
        "Presence of this container.";
      description
        "Contains Aggregation Port configuration related nodes,
        which provides the basic management controls necessary
        to allow an instance of an Aggregation Port to be managed,
        for the purposes of Link Aggregation.";
      container aggregation-port-lacp {
        description
          "Contains Aggregation port LACP configuration related
          nodes.";
        leaf actor-admin-key {
          type int16;
          description
            "The current administrative value of the Key for the
            Aggregation Port. The meaning of particular Key values
            is of local significance.";
          reference
            "IEEE 802.1AX-2008, Clause 6.3.2.1.4";
        }
      } // aggregation-port-lacp
    } // aggregation-port
  } // augment interfaces


} // ieee802-dot1ax
