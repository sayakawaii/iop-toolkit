module nokia-ietf-ip-inband-no-ipv4-dev {

  namespace "http://www.nokia.com/Fixed-Networks/BBA/yang/"
            + "nokia-ietf-ip-inband-no-ipv4-dev";

  prefix nokia-ietf-ip-inband-no-ipv4-dev;

  import ietf-interfaces {
    prefix if;
  }

  import ietf-ip {
    prefix ip;
  }

  import iana-if-type {
    prefix ianaift;
  }

  organization
    "Nokia";

  contact
    "Comments or questions about this Nokia YANG module should be
     directed to <mailto:isam.yang@nokia.com>.";

  description
    "This module contains a collection of YANG deviations on top
     of ietf-ip module to support l2 forwarding termination
     functionality.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2017-2018, Nokia. All Rights Reserved.";

  revision 2024-11-07 {
    description "Typeb x-shelf changes.";
    reference "Nokia specific";
  }

  revision 2022-12-14 {
    description
      "Introduced to block configuration of unique-local ipv6 address in NTs,LTs";
    reference
      "BBN-119888";
  }

  revision 2019-10-17 {
    description
      "Introduced to block inband connectivity over ipv4 address for SDFX.";
    reference
      "Nokia specific";
  }

  /****************************************************************************/
  /* inband connectivity over ipv4 address is is only supported on IHUB-NE    */
  /****************************************************************************/

  deviation "/if:interfaces/if:interface/ip:ipv4/ip:address/ip:ip"  {
    deviate add {
        must "not(contains(.,'.'))" {
        error-message "inband connectivity over ipv4 address is only supported on IHUB-NE.";
        description "inband connectivity over ipv4 address is only supported on IHUB-NE";
       }
    }
  }

  /****************************************************************************/
  /* IPv4 can enable/disable only on interface type ipForward.                */
  /****************************************************************************/
  deviation "/if:interfaces/if:interface/ip:ipv4/ip:enabled"  {
    /* IPv4 can enable/disable only on interface type ipForward. */
    deviate add {
        must "(../../if:type = 'ianaift:ipForward')" {
        error-message "IP interface type should be ipForward.";
        description "IPv4 is only supported on top ipForward interface";
      }
    }
  }

  deviation "/if:interfaces/if:interface/ip:ipv6/ip:address/ip:ip"  {
    deviate add {
      must "(substring-before(.,':') != 'fd00')"{
            error-message "Invalid IP. Unique-local address is a not valid address";
            description "A unique-local address cannot be configured in an ipForward interface";
      }
    }
  }
}
