module nokia-sdan-keyword-alignment-aug {
  yang-version 1.1;
  namespace "http://www.nokia.com/Fixed-Networks/BBA/yang/"
          + "nokia-sdan-keyword-alignment-aug";
  prefix nokia-sdan-keyword-alignment-aug;

  import ietf-system {
    prefix sys;
  }

  import bbf-subscriber-profiles{
    prefix bbf-subprof;
  }

  organization
    "Nokia";

  contact
    "Comments or questions about this Nokia YANG module should be
     directed to <mailto:isam.yang@nokia.com>.";

  description
    "This module contains a collection of YANG definitions for
     supporting Nokia specific requirements as applicable to its
     access network equipment.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2025, Nokia. All Rights Reserved.";

  revision 2025-02-18 {
    description
      "Initial revision.
       * Approval Date:    see revision date above.
       * Publication Date: yyyy-mm-dd.";
    reference
      "Nokia specific";
  }

  augment "/sys:system/bbf-subprof:subscriber-management" {
    description "augment subscriber management with onu slot/port minimum string length";
    leaf onu-slot-minimum-string-length {
      type uint8 {
        range "1..5";
      }
      default 1;
      description
         "This leaf determines if the ONU slot numbering MUST
          use leading 0's or not, and how many 0's are added to
          achieve the desired string length.
          e.g., configuring 2 and if slot-id = 1, keyword Onuslot will be replaced by value 01.
          It indicates the minimum string length and actual value can be larger if needed.
          e.g., configuring 1 and slot-id = 12 would be allowed since string length 2 >= 1";
    }

    leaf onu-port-minimum-string-length {
      type uint8 {
        range "1..5";
      }
      default 1;
      description
         "This leaf determines if the ONU port numbering MUST
          use leading 0's or not, and how many 0's are added to
          achieve the desired string length.
          e.g., configuring 2 and if port-id = 1, keyword Onuport will be replaced by value 01.
          It indicates the minimum string length and actual value can be larger if needed.
          e.g., configuring 1 and port-id = 12 would be allowed since string length 2 >= 1";
    }
  }
}
