module nokia-vlan-sub-interface-vector-ipv6-address-spoofing-prevention {
  yang-version 1.1;
  namespace "uri:http://www.nokia.com/Fixed-Networks/BBA/yang/"
          + "nokia-vlan-sub-interface-vector-ipv6-address-spoofing-prevention";
  prefix nokia-vector-ipv6-sppr;

  import bbf-vlan-sub-interface-vector {
    prefix bbf-vsi-vctr;
  }

  organization
    "Nokia";

  contact
    "Comments or questions about this Nokia YANG module should be
    directed to <mailto:isam.yang@nokia.com>.";

  description
    "This module contains a collection of YANG definitions for
     supporting the Broadband Forum requirements on the management of
     sub-interfaces as applicable to access network equipment. As
     such, this module is specific to access network equipment (e.g.,
     BBF-specified Access Nodes and FTTdp DPUs).

     Specifically, this module extends the VLAN sub-interface vector 
     profile concept with data nodes supporting the frame processing
     profile.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.
 
     The product specifications and other technical or performance
     information contained herein are subject to change without
     notice. Updates of this document will be issued under the above
     NDA's.
 
     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
 
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
 
     Nokia reserves the right not to offer any or all of these
     products and to withdraw any or all of them at any future time.
 
     Copyright (C) 2021, Nokia. All Rights Reserved.";

  revision 2021-12-06 {
    description
      "Initial revision.
       * Approval Date:    see revision date above.
       * Publication Date: 20xx-xx-xx.";
    reference
      "TR-383: Common YANG Modules
               <https://www.broadband-forum.org/technical/download/
                        TR-383.pdf>";
  }

  revision 2021-08-20 {
    description
      "Initial revision.
       * Approval Date:    see revision date above.
       * Publication Date: 20xx-xx-xx.";
    reference
      "TR-383: Common YANG Modules
               <https://www.broadband-forum.org/technical/download/
                        TR-383.pdf>";
  }
  feature learn-addresses-from-icmpv6 {
    description
      "Learn IPv6 global unicast addresses from the IPv6 stateless
       Neighbour Discovery protocol, Router Advertisment messages.";
  }

  augment "/bbf-vsi-vctr:vsi-vector-profiles"
        + "/bbf-vsi-vctr:vsi-vector-profile" {
    description "augment vsi vector of profiles with ipv6-security";
    container ipv6-security {
      presence
        "Presence of this container indicates IPv6 anti-spoofing is supported on
         this interface.";

      description
        "This container provides configuration data that assures there
         is knowledge on the interface on the IPv6 addresses used by
         the device connected to the interface.";

      leaf prevent-ipv6-address-spoofing {
        type boolean;
        default "false";
        description
          "When 'true', the system will perform IPv6 address security
           checks on the VLAN sub-interface. This means that checks
           are performed on packets received or to be send on a VLAN
           sub-interface. To do these checks it needs to know which
           IPv6 addresses are assigned to the VLAN sub-interface. How
           addresses get assigned is subject to configration defined
           in the container ipv6-addresses.

           The security checks performed are:
           - applicable to all IPv6 packets that contain a global
             unicast address as source IP address.
           - not applicable to IPv6 packets that
             contain a link-local address as source IP address, i.e.
             not applicable to the source IP address of ICMPv6 and
             DHCPv6 packets.
           - Only accept incoming IPv6 packets when the global unicast
             source address is assigned to the interface.
           Packets with an IPv6 address not passing the test are
           discarded.

           When 'false', no checks on the IPv6 address are
           performed.";

        reference
          "TR-177i1 - R22";
      }

      leaf learn-addresses-from-dhcpv6 {
        type empty;
        must '../prevent-ipv6-address-spoofing = '
            +'"true"' {
          error-message "Before enable learn-addresses-from-dhcp,prevent-ipv6-address-spoofing should be enabled;
                      Before disable prevent-ipv6-address-spoofing ,learn-addresses-from-dhcp should be disabled.";
        }

        description
          "When set, the system will learn IPv6 addresses from the
           DHCPv6 messages passing the VLAN sub-interface, and assign
           them to the VLAN sub-interface.";

        reference
          "TR-177i1 - R121";
      }

      leaf learn-addresses-from-icmpv6 {
        if-feature learn-addresses-from-icmpv6;
        type empty;
        must '../prevent-ipv6-address-spoofing = '
            +'"true"' {
          error-message "Before enable learn-addresses-from-dhcp,prevent-ipv6-address-spoofing should be enabled;
                      Before disable prevent-ipv6-address-spoofing ,learn-addresses-from-dhcp should be disabled.";
        }
        description
          "When set, the system will learn IPv6 addresses from the
           IPv6 stateless Neighbour Discovery protocol, Router
           Advertisment messages passing the VLAN sub-interface.";

        reference
          "TR-177i1 - R121";
      }

      leaf max-address {
        type union {
          type enumeration {
            enum "no-limit" {
              description
                "Used to indicate that all profiles are allowed.";
            }
          }
          type uint32;
        }
        must 'current() = "no-limit"'
            + 'or ../prevent-ipv6-address-spoofing = '
            +'"true"' {
          error-message "Before create max-address,prevent-ipv6-address-spoofing should be enabled;
                        Before disable prevent-ipv6-address-spoofing, max-address should be deleted.";
        }
        default "no-limit";
        description
          "Specifies the maximum number of IPv6 address (static and dynamic)
           allowed for VLAN sub-interfaces where the default value no-limit
           refers that there is no restriction";
      }
    }    
  }
}
