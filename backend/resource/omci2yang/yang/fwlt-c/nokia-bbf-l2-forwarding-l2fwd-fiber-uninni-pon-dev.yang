module nokia-bbf-l2-forwarding-l2fwd-fiber-uninni-pon-dev {

  namespace "http://www.nokia.com/Fixed-Networks/BBA/yang/" +
            "nokia-bbf-l2-forwarding-l2fwd-fiber-uninni-pon-dev";

  prefix nokia-bbf-l2-forwarding-l2fwd-fiber-uninni-pon-dev;

  import bbf-l2-forwarding {
    prefix bbf-l2-fwd;
  }

  organization
    "Nokia";

  contact
    "isam.yang@nokia.com";

  description
    "This module contains a collection of YANG deviations on top
     of standard for supporting BBF/bbf-l2-forwarding YANG module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2017-2018, Nokia. All Rights Reserved.";

  revision 2024-01-31 {
    description
      "move deviations from l2fwd-fiber-uninni";
    reference
      "Nokia specific";
  }

  revision 2021-02-26 {
    description
      "Initial revision.";
    reference
      "Nokia specific";
  }

  deviation "/bbf-l2-fwd:forwarding/bbf-l2-fwd:flooding-policies-profiles/bbf-l2-fwd:flooding-policies-profile/bbf-l2-fwd:flooding-policy"{
    deviate add {
      must "count(current()/bbf-l2-fwd:in-interface-usages[bbf-l2-fwd:interface-usages = 'subtended-node-port']) = 0"
      {
        error-message "Does not support configured subtended-node-port upstream flooding policy.";
      }
    }

  }

    deviation "/bbf-l2-fwd:forwarding/bbf-l2-fwd:flooding-policies-profiles/bbf-l2-fwd:flooding-policies-profile/bbf-l2-fwd:flooding-policy"{
    /*
    * for DownStream, if ipv4-multicast-address flooding, the ntp-multicast-address must flooding to user-port and subtended-node-port
    */
    deviate add{
        must "not((./bbf-l2-fwd:in-interface-usages/bbf-l2-fwd:interface-usages = 'network-port' and
                  (count(./bbf-l2-fwd:out-interface-usages[bbf-l2-fwd:interface-usages = 'user-port']) = 0 or
                   count(./bbf-l2-fwd:out-interface-usages[bbf-l2-fwd:interface-usages = 'subtended-node-port']) = 0) and
                   boolean(./bbf-l2-fwd:destination-address/bbf-l2-fwd:ntp-multicast-address))
                  and
                  (count(../bbf-l2-fwd:flooding-policy[./bbf-l2-fwd:in-interface-usages/bbf-l2-fwd:interface-usages = 'network-port' and
                                                 ./bbf-l2-fwd:destination-address/bbf-l2-fwd:ipv4-multicast-address and
                                                 ./bbf-l2-fwd:discard]) = 0)
                  )"
        {
           error-message "NTP multicast must flooding to user-port and subtended-node-port if no ipv4-multicast-address discard exist";
        }
    }

    /*
     * for DownStream, if ipv4-multicast-address flooding, the rip-multicast-address must flooding to user-port and subtended-node-port
     * there another deviation will request downstream rip-multicast-address must flooding to subtended-node-port
     * so, there only need judge user-port in this deviation
     */
    deviate add{
        must "not((./bbf-l2-fwd:in-interface-usages/bbf-l2-fwd:interface-usages = 'network-port' and
                  (count(./bbf-l2-fwd:out-interface-usages[bbf-l2-fwd:interface-usages = 'user-port']) = 0 or
                   count(./bbf-l2-fwd:out-interface-usages[bbf-l2-fwd:interface-usages = 'subtended-node-port']) = 0) and
                   boolean(./bbf-l2-fwd:destination-address/bbf-l2-fwd:rip-multicast-address))
                  and
                  (count(../bbf-l2-fwd:flooding-policy[./bbf-l2-fwd:in-interface-usages/bbf-l2-fwd:interface-usages = 'network-port' and
                                                 ./bbf-l2-fwd:destination-address/bbf-l2-fwd:ipv4-multicast-address and
                                                 ./bbf-l2-fwd:discard]) = 0)
                  )"
        {
           error-message "rip multicast must flooding to user-port and subtended-node-port if no ipv4-multicast-address discard exist";
        }
    }
  }
}
