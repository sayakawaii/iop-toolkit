module nokia-sdan-system-restart-reason-types {
  yang-version 1.1;
   
  namespace "http://www.nokia.com/Fixed-Networks/BBA/yang/"
           + "nokia-sdan-system-restart-reason-types";
 
  prefix nokia-sdan-sysrestartt;
 
  organization
    "Nokia";
    
  contact
    "Comments or questions about this Nokia YANG module should be
     directed to <mailto:isam.mibsupport@nokia.com>.";
    
  description
    "This module contains a collection of YANG definitions for
     supporting Nokia specific requirements as applicable to its
     access network equipment.
    
     Specifically, this module contains a collection of YANG
     identities related to ONU restart.
    
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.
    
     The product specifications and other technical or performance
     information contained herein are subject to change without
     notice. Updates of this document will be issued under the above
     NDA's.
    
     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
    
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
    
     Nokia reserves the right not to offer any or all of these
     products and to withdraw any or all of them at any future time.
    
     Copyright (C) 2021, Nokia. All Rights Reserved.";
    
    
  revision 2022-10-13 {
    description
      "Initial revision.
       * Approval Date:    see revision date above.
       * Publication Date: yyyy-mm-dd.";
    reference
      "Nokia specific";
  }
 
  identity restart-reason-base {
    description
      "Base identity to reflect the reason why the system
       restarted.";
  }
 
  identity external-restart-request{
    base restart-reason-base;
    description
      "The system restarted because of an external request.";
  }
 
  identity remote-software-restart-request{
    base external-restart-request;
    description
      "A software restart was requested via a remote OAM
       Interface.";
  }
 
  identity local-hardware-restart-request{
    base external-restart-request;
    description
      "A manual hardware restart was locally requested.";
  }
 
  identity local-software-restart-request{
    base external-restart-request;
    description
      "A software restart was requested via a local OAM
       interface such as craft or WEB interface.";
  }
 
  identity autonomous-software-trigger{
    base restart-reason-base;
    description
      "The system restarted due to an autonomous
       software reason.";
  }
 
  identity software-time-out{
    base autonomous-software-trigger;
    description
      "The system restarted because of a software time-out.";
  }
 
  identity out-of-memory{
    base autonomous-software-trigger;
    description
      "The system restarted because the software ran out
       of memory.";
  }
 
  identity undetermined-software-error{
    base autonomous-software-trigger;
    description
      "The system restarted because the software encountered
       an undetermined error such as unresolvable references,
       critical internal inconsistency.";
  }
  
  identity autonomous-hardware-trigger{
    base restart-reason-base;
    description
      "The system restarted due to an autonomous
       hardware reason.";
  }
 
  identity over-temperature{
    base autonomous-hardware-trigger;
    description
      "The system restarted because of an over-temperature
       condition.";
  }
 
  identity undetermined-hardware-error{
    base autonomous-hardware-trigger;
    description
      "The system restarted because of an undetermined hardware
       condition such as bus time-out, misaligned memory access,
       abnormal voltage monitor.";
  }
 
  identity undetermined-restart-reason{
    base restart-reason-base;
    description
      "The system restarted because of an undetermined reason.";
  }
 
  identity reason-not-reported{
    base undetermined-restart-reason;
    description
      "The system is unable to report the restart reason.";
  }
}
