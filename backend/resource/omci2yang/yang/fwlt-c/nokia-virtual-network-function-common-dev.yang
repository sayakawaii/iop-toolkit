module nokia-virtual-network-function-common-dev {
  yang-version "1.1";
  namespace "http://www.nokia.com/Fixed-Networks/BBA/yang/nokia-virtual-network-function-common-dev";
  prefix nokia-vnf-common-dev;

  import nokia-virtual-network-function {
    prefix "nokia-vnf";
  }

  import iana-tls-cipher-suite-algs {
        prefix "tlscsa";
  }
  
  organization "Nokia";

  contact
    "Comments or questions about this Nokia YANG module should be
     directed to <mailto:isam.yang@nokia.com>.";

  description
    "The NOKIA common/nokia-ietf-netconf-acm-common-dev YANG module
         supporting deviations on top of ietf-netconf-acm standard.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2026-09-01 {
    description "Initial Version";
    reference "Nokia specific";
  }

deviation "/nokia-vnf:virtual-network-functions/nokia-vnf:virtual-network-function/nokia-vnf:tls/nokia-vnf:server-auth" {
      deviate delete { must 'pinned-ca-certs or pinned-server-certs';}
  }
  
  
  deviation "/nokia-vnf:virtual-network-functions/nokia-vnf:virtual-network-function/nokia-vnf:tls/nokia-vnf:server-auth/nokia-vnf:pinned-server-certs" {
      description
      "Pinned server certs is no longer supported";
      deviate not-supported;
  }
  

  deviation "/nokia-vnf:virtual-network-functions/nokia-vnf:virtual-network-function/nokia-vnf:tls/nokia-vnf:server-auth/nokia-vnf:pinned-ca-certs" {
      deviate add {
       must "not(../est-certificate-profile)"{
          error-message "Exactly one authentication mechanism (EST certificate profile, or CA pinning) must be specified";
          description "Specify exactly one authentication mechanism (EST certificate profile or CA pinning)";
        }
      }
    }
  
   deviation "/nokia-vnf:virtual-network-functions/nokia-vnf:virtual-network-function/nokia-vnf:tls/nokia-vnf:client-identity/nokia-vnf:auth-type/nokia-vnf:certificate/nokia-vnf:certificate/nokia-vnf:local-or-keystore/nokia-vnf:keystore/nokia-vnf:reference" {
        deviate not-supported;
    }
  
  
    deviation "/nokia-vnf:virtual-network-functions/nokia-vnf:virtual-network-function/nokia-vnf:tls/nokia-vnf:client-identity/nokia-vnf:auth-type/nokia-vnf:certificate/nokia-vnf:certificate/nokia-vnf:local-or-keystore/nokia-vnf:local" {
        deviate not-supported;
    }

     deviation "/nokia-vnf:virtual-network-functions/nokia-vnf:virtual-network-function/nokia-vnf:tls/nokia-vnf:client-identity/nokia-vnf:auth-type/nokia-vnf:certificate/nokia-vnf:certificate/nokia-vnf:local-or-keystore/nokia-vnf:keystore/nokia-vnf:certificate-reference-choice/nokia-vnf:central-keystore-reference/nokia-vnf:central-keystore-reference/nokia-vnf:asymmetric-key" {
         deviate add {
            must '../certificate' {
                error-message "'asymmetric-key' must be configured together with 'certificate' under 'central-keystore-reference'";
                description "'asymmetric-key' must be configured together with 'certificate' under 'central-keystore-reference'.";
            }
         }
    }


    deviation "/nokia-vnf:virtual-network-functions/nokia-vnf:virtual-network-function/nokia-vnf:tls/nokia-vnf:hello-params/nokia-vnf:cipher-suites/nokia-vnf:cipher-suite" {
        description "The YANG identifiers of the supported ciphers ordered by descending preference";
        deviate add {
            must "(current() = 'tlscsa:tls-aes-256-gcm-sha384' or current() = 'tlscsa:tls-chacha20-poly1305-sha256'"+
                "or current() = 'tlscsa:tls-aes-128-gcm-sha256' or current() = 'tlscsa:tls-ecdhe-rsa-with-aes-256-gcm-sha384'"+
                "or current() = 'tlscsa:tls-ecdhe-rsa-with-chacha20-poly1305-sha256' or current() = 'tlscsa:tls-ecdhe-rsa-with-aes-128-gcm-sha256'"+
                "or current() = 'tlscsa:tls-ecdhe-rsa-with-aes-256-cbc-sha384' or current() = 'tlscsa:tls-ecdhe-rsa-with-aes-256-cbc-sha'"+
                "or current() = 'tlscsa:tls-rsa-with-aes-256-gcm-sha384' or current() = 'tlscsa:tls-rsa-with-aes-256-cbc-sha256'"+
                "or current() = 'tlscsa:tls-rsa-with-aes-256-cbc-sha' or current() = 'tlscsa:tls-ecdhe-rsa-with-aes-128-cbc-sha256'"+
                "or current() = 'tlscsa:tls-ecdhe-rsa-with-aes-128-cbc-sha' or current() = 'tlscsa:tls-rsa-with-aes-128-gcm-sha256'"+
                "or current() = 'tlscsa:tls-rsa-with-aes-128-cbc-sha256' or current() = 'tlscsa:tls-rsa-with-aes-128-cbc-sha')"{
                error-message "this cipher is not supported";
                description "The YANG identifiers of the supported ciphers ordered by descending preference";
            }
        }
    }

      deviation "/nokia-vnf:virtual-network-functions/nokia-vnf:virtual-network-function/nokia-vnf:type" {
        description
        "At most one virtual-network-function can have type pskmgnt";
        deviate add {
          must ". != 'pskmgnt' or count(/nokia-vnf:virtual-network-functions/nokia-vnf:virtual-network-function[nokia-vnf:type='pskmgnt']) <= 1" {
            error-message "At most one virtual-network-function with type 'pskmgnt' is allowed";
            description "No restriction applies when type is not pskmgnt";
          }
        }
      }


}
