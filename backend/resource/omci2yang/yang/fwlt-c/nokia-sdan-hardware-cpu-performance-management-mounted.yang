module nokia-sdan-hardware-cpu-performance-management-mounted {
  yang-version 1.1;
  namespace "http://www.nokia.com/Fixed-Networks/BBA/yang/"
          + "nokia-sdan-hardware-cpu-performance-management-mounted";
  prefix nokia-cpu-pm-mgnt-mounted;

  import bbf-fiber-onu-emulated-mount {
    prefix onu;
  }
  import bbf-yang-types {
    prefix bbf-yang;
  }
  import iana-hardware {
    prefix ianahw;
  }
  import ietf-hardware-mounted {
    prefix hw-mounted;
  }
  import nokia-hardware-profiles-mounted {
    prefix nokia-hw-prof-mounted;
  }
  import nokia-sdan-hardware-pm-threshold-profiles-mounted {
    prefix nokia-hw-pm-threshold-prof-mounted;
  }
  import bbf-interfaces-performance-management-mounted {
    prefix bbf-if-pm-mounted;
  }

  organization
    "Nokia";
  contact
    "Comments or questions about this Nokia YANG module should be
     directed to <mailto:isam.yang@nokia.com>.";
  description
    "This module contains a collection of YANG definitions for
     supporting Nokia specific requirements as applicable to its
     access network equipment.

     Specifically, this module augments the hardware model with data
     that supports configuring performance monitoring and thresholding.
     Also augments the hardware model with performance monitoring
     data of a CPU component.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2025-10-10 {
    description
      "TCA validation added CPU component";
    reference
      "BBN-301538";
  }

  revision 2025-06-04 {
    description
      "PM counter group support for CPU";
    reference
      "Nokia specific for EPIC BBN-107831";
  }

  revision 2022-05-16 {
    description
      "Augments hardware componenet with CPU as class to attach TCA profiles.";
    reference
      "Nokia specific.";
  }

  feature performance-24hr {
    description
      "Indicates that collection of 24 hour performance intervals
       is supported.";
  }

  augment "/onu:onus/onu:onu/onu:root/hw-mounted:hardware/hw-mounted:component" {
    description "augment hw component cpu";
    container performance {
      presence "If container is not present, CPU performance monitoring is disabled.
                If container is present CPU performance monitoring is disabled or enabled
                depending on the value of 'enable' leaf.";
      description
        "Performance parameters.";
      leaf enable {
        type boolean;
	must "../../hw-mounted:class = 'ianahw:cpu'"{
          error-message
            "The enable flag of this container is supported only for CPU components";
        }
        default "false";
        description
          "If true, enables performance monitoring on this hardware component.
           The performance data will be available under
           '/onu:onus/onu:onu/onu:root/hw-mounted:hardware-state/hw-mounted:component/'
           for 15 minute and, if supported, 24 hour current and
           historic intervals.
           If false, then there are no performance data available
           on this hardware component.";
      }
      leaf cpu-tca-profile {
        type leafref {
          path "../../../../nokia-hw-prof-mounted:tca-profiles/nokia-hw-pm-threshold-prof-mounted:pm-profiles/nokia-hw-pm-threshold-prof-mounted:system-load-profile/nokia-hw-pm-threshold-prof-mounted:name";
        }
	 must "../../hw-mounted:class = 'ianahw:cpu'"{
          error-message
            "This TCA profile must be associated only to the CPU components";
        }
        description
          "Reference to a CPU threshold profile. Allowes to configure threshold values
           for CPU performance monitoring data. TCA is disabled when no profile is
           referenced. This has no effect when performance monitoring is disabled";
      }
      leaf memory-tca-profile {
        type leafref {
          path "../../../../nokia-hw-prof-mounted:tca-profiles/nokia-hw-pm-threshold-prof-mounted:pm-profiles/nokia-hw-pm-threshold-prof-mounted:memory-usage-profile/nokia-hw-pm-threshold-prof-mounted:name";
        }
	must "../../hw-mounted:class = 'ianahw:cpu'"{
	  error-message
	    "This TCA profile must be associated only to the CPU components";
	}
        description
          "Reference to a memory threshold profile. Allowes to configure threshold values
           for memory performance monitoring data. TCA is disabled when no profile is
           referenced. This has no effect when performance monitoring is disabled";
      }
      leaf-list cpu-mem-util-group {
	type cpu-mem-util-group-type;
	must "../../hw-mounted:class = 'ianahw:cpu'"{
	  error-message
	    "This TCA profile must be associated only to the CPU components";
	}
	description
	      "Performance monitoring group type to enable or disable
	      specific performance monitoring counters";
      }
    }
  }

  grouping cpu-performance {
    description "grouping cpu performance";
    container system-load {
      description
        "Performance monitoring data associated with CPU utilization.";
      leaf average-system-load {
        type bbf-yang:percent;
        units "percent";
        description
          "The average calculated system load over the performance monitoring period.";
      }
    }
  }

  grouping memory-usage {
    description "grouping memory usage";
    container memory-usage {
      description
        "Performance monitoring data associated with memory utilization.";
      leaf total-mem {
        type bbf-yang:performance-counter64;
        units "kibibytes";
        description
          "Total memory available in kibibytes(KiB), including free and used.";
      }
      leaf used-mem {
        type bbf-yang:performance-counter64;
        units "kibibytes";
        description
          "Total memory used in kibibytes(KiB). This is an instantaneous value.";
      }
    }
  }

  augment "/onu:onus/onu:onu/onu:root/hw-mounted:hardware-state/hw-mounted:component" {
    when 'derived-from-or-self (hw-mounted:class,"ianahw:cpu")' {
      description
        "Augments the hardware model with performance monitoring
         data of a CPU component";
    }
    description
      "Data nodes for hardware components of identity class 'cpu'.";
    container performance {
      description
        "Performance monitoring parameters.";
      container intervals-15min {
        description
          "15 minute interval performance history.";
        container current {
          description
            "Contains the performance data for the current interval.";
          uses cpu-performance;
        }
        uses bbf-if-pm-mounted:performance-15min-history-parameters;
        list history {
          key "interval-number";
          max-elements 96;
          description
            "A history of 15 minute intervals.";
          leaf interval-number {
            type bbf-if-pm-mounted:performance-15min-history-interval;
            description
              "The number of the interval relative to the current interval.";
          }
          uses bbf-if-pm-mounted:performance-history-15min-interval-parameters;
          uses cpu-performance;
        }
      }
      container intervals-24hr {
        if-feature "performance-24hr";
        description
          "24 hour interval performance history.";
        container current {
          description
            "Contains the performance data for the current interval.";
          uses memory-usage;
        }
        uses bbf-if-pm-mounted:performance-24hr-history-parameters;
        list history {
          key "interval-number";
          max-elements 7;
          description
            "A history of 24 hour intervals.";
          leaf interval-number {
            type bbf-if-pm-mounted:performance-24hr-history-interval;
            description
              "The number of the interval relative to the current interval.";
          }
          uses bbf-if-pm-mounted:performance-history-24hr-interval-parameters;
          uses memory-usage;
        }
      }
    }
  }
  typedef cpu-mem-util-group-type {
      type enumeration {
          enum "cpu-util-pm" {
              description
                "This enables the performance monitoring for cpu utilization in hardware component.
                When this PM counter group is enabled, the current and history performance data for below xpaths are enabled
                    - hardware-state/component/performance/current/system-load
                    - hardware-state/component/performance/history/system-load";
          }
          enum "mem-usage-pm" {
              description
                "This enables the performance monitoring for memory usage in hardware component.
                When this PM counter group is enabled, the current and history performance data for below xpaths are enabled
                    - hardware-state/component/performance/current/memory-usage
                    - hardware-state/component/performance/history/memory-usage";
          }
      }
      description
	"cpu memory util pm group type";
  }
}
