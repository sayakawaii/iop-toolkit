module bbf-subscriber-types {
  yang-version 1.1;
  namespace "urn:bbf:yang:bbf-subscriber-types";
  prefix bbf-subtype;

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     WA Director: Joey Boyd, ADTRAN

     WA Director: Sven Ooghe, Nokia";
  description
    "This module contains a collection of YANG definitions for
     supporting the Broadband Forum requirements on the management of
     subscribers as applicable to access network equipment. As such,
     this module is specific to access network equipment (e.g.,
     BBF-specified Access Nodes and FTTdp DPUs).

     Specifically, this module defines common types associated with
     subscribers and subscriber protocols.

     Copyright (c) 2017-2022, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a5; see
     the TR itself for full legal notices.";

  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }
  revision 2017-05-08 {
    description
      "Initial revision.
       * Approval Date:    see revision date above.
       * Publication Date: 2017-06-02.";

    reference
      "TR-383: Common YANG Modules
               <https://www.broadband-forum.org/technical/download/
                        TR-383.pdf>";
  }

  typedef broadband-line-characteristics {
    type bits {
      bit actual-data-rate-upstream {
        description
          "Sub-option type 0x81 - Actual upstream data rate of an
           access loop.";

        reference
          "TR-101i2 Table 3, sub-TLV 0x81
           ITU-T G.997.1 Section 7.5.2.1
           TR-301i2 Table 14-1, sub-TLV 129
           ITU-T G.997.2 Section 7.11.1.1";
      }
      bit actual-data-rate-downstream {
        description
          "Sub-option type 0x82 - Actual downstream data rate of an
           access loop.";

        reference
          "TR-101i2 Table 3, sub-TLV 0x82
           ITU-T G.997.1 Section 7.5.2.1
           TR-301i2 Table 14-1, sub-TLV 130
           ITU-T G.997.2 Section 7.11.1.1";
      }
      bit min-data-rate-upstream {
        description
          "Sub-option type 0x83 - Minimum upstream data rate at which
           the loop is set to operate.";

        reference
          "TR-101i2 Table 3, sub-TLV 0x83
           ITU-T G.997.1 Section 7.3.2.1.1";
      }
      bit min-data-rate-downstream {
        description
          "Sub-option type 0x84 - Minimum downstream data rate at
           which the loop is set to operate.";

        reference
          "TR-101i2 Table 3, sub-TLV 0x84
           ITU-T G.997.1 Section 7.3.2.1.1";
      }
      bit attainable-data-rate-upstream {
        description
          "Sub-option type 0x85 - Maximum upstream data rate that can
           be achieved.";

        reference
          "TR-101i2 Table 3, sub-TLV 0x85
           ITU-T G.997.1 Section 7.5.1.20 (ATTNDRus)
           TR-301i2 Table 14-1, sub-TLV 133
           ITU-T G.997.2 Section 7.11.2.1";
      }
      bit attainable-data-rate-downstream {
        description
          "Sub-option type 0x86 - Maximum downstream data rate that
           can be achieved.";

        reference
          "TR-101i2 Table 3, sub-TLV 0x86
           ITU-T G.997.1 Section 7.5.1.19 (ATTNDRds)
           TR-301i2 Table 14-1, sub-TLV 134
           ITU-T G.997.2 Section 7.11.2.1";
      }
      bit max-data-rate-upstream {
        description
          "Sub-option type 0x87 - Maximum upstream data rate at which
           the loop is set to operate.";

        reference
          "TR-101i2 Table 3, sub-TLV 0x87
           ITU-T G.997.1 Section 7.3.2.1.3";
      }
      bit max-data-rate-downstream {
        description
          "Sub-option type 0x88 - Maximum downstream data rate at
           which the loop is set to operate.";

        reference
          "TR-101i2 Table 3, sub-TLV 0x88
           ITU-T G.997.1 Section 7.3.2.1.3";
      }
      bit min-data-rate-upstream-low-power-state {
        description
          "Sub-option type 0x89 - Minimum upstream data rate at which
           the loop is set to operate during the low power state
           (L1/L2).";

        reference
          "TR-101i2 Table 3, sub-TLV 0x89
           ITU-T G.997.1 Section 7.3.2.1.5";
      }
      bit min-data-rate-downstream-low-power-state {
        description
          "Sub-option type 0x8A - Minimum downstream data rate at
           which the loop is set to operate during the low power
           state (L1/L2).";

        reference
          "TR-101i2 Table 3, sub-TLV 0x8A
           ITU-T G.997.1 Section 7.3.2.1.5";
      }
      bit max-interleaving-delay-upstream {
        description
          "Sub-option type 0x8B - Maximum one-way interleaving delay
           in upstream.";

        reference
          "TR-101i2 Table 3, sub-TLV 0x8B
           ITU-T G.997.1 Section 7.3.2.2";
      }
      bit actual-interleaving-delay-upstream {
        description
          "Sub-option type 0x8C - Actual one-way interleaving delay
           value in milliseconds corresponding to the interleaver
           setting in upstream.";

        reference
          "TR-101i2 Table 3, sub-TLV 0x8C
           ITU-T G.997.1 Section 7.5.2.3";
      }
      bit max-interleaving-delay-downstream {
        description
          "Sub-option type 0x8D - Maximum one-way interleaving delay
           in downstream.";

        reference
          "TR-101i2 Table 3, sub-TLV 0x8D
           ITU-T G.997.1 Section 7.3.2.2";
      }
      bit actual-interleaving-delay-downstream {
        description
          "Sub-option type 0x8E - Actual one-way interleaving delay
           value in milliseconds corresponding to the interleaver
           setting in downstream.";

        reference
          "TR-101i2 Table 3, sub-TLV 0x8E
           ITU-T G.997.1 Section 7.5.2.3";
      }
      bit access-loop-encapsulation {
        description
          "Sub-option type 0x90 - the data link protocol and the
           encapsulation overhead on the access loop.";

        reference
          "TR-101i2 - R164";
      }
      bit expected-throughput-upstream {
        description
          "Expected throughput (ETR) upstream.";
        reference
          "TR-301i2 Table 14-1, sub-TLV 155
           ITU-T G.997.2 Section 7.11.1.2";
      }
      bit expected-throughput-downstream {
        description
          "Expected throughput (ETR) downstream.";
        reference
          "TR-301i2 Table 14-1, sub-TLV 156
           ITU-T G.997.2 Section 7.11.1.2";
      }
      bit attainable-expected-throughput-upstream {
        description
          "Attainable expected throughput (ATTETR) upstream.";
        reference
          "TR-301i2 Table 14-1, sub-TLV 157
           ITU-T G.997.2 Section 7.11.2.2";
      }
      bit attainable-expected-throughput-downstream {
        description
          "Attainable expected throughput (ATTETR) downstream.";
        reference
          "TR-301i2 Table 14-1, sub-TLV 158
           ITU-T G.997.2 Section 7.11.2.2";
      }
      bit gamma-data-rate-upstream {
        description
          "Gamma data rate (GDR) upstream.";
        reference
          "TR-301i2 Table 14-1, sub-TLV 159
           ITU-T G.997.2 Section 7.11.1.3.";
      }
      bit gamma-data-rate-downstream {
        description
          "Gamma data rate (GDR) downstream.";
        reference
          "TR-301i2 Table 14-1, sub-TLV 160
           ITU-T G.997.2 Section 7.11.1.3";
      }
      bit attainable-gamma-data-rate-upstream {
        description
          "Attainable gamma data rate (ATTGDR) upstream.";
        reference
          "TR-301i2 Table 14-1, sub-TLV 161
           ITU-T G.997.2 Section 7.11.2.3";
      }
      bit attainable-gamma-data-rate-downstream {
        description
          "Attainable gamma data rate (ATTGDR) downstream.";
        reference
          "TR-301i2 Table 14-1, sub-TLV 162
           ITU-T G.997.2 Section 7.11.2.3";
      }
    }
    description
      "The type defined for the broadband line characteristics
       listed in TR-101i2 and TR-301i2";

    reference
      "TR-101i2 - R158, TR-301i2 - R119";
  }
}
