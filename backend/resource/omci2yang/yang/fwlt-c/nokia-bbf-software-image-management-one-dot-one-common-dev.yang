module nokia-bbf-software-image-management-one-dot-one-common-dev {

  namespace
    "http://www.nokia.com/Fixed-Networks/BBA/yang/nokia-bbf-software-image-management-one-dot-one-common-dev";

  prefix "nokia-bbf-software-image-management-one-dot-one-common-dev";

  import bbf-software-image-management-one-dot-one {
     prefix bbf-sim;
  }

  import ietf-hardware {
    prefix hw;
  }

  import bbf-yang-types {
    prefix bbf-yang;
  }

  organization
       "BBF/NOKIA";

  contact
       "Comments or questions about this Nokia YANG module should be
       directed to <mailto:isam.yang@nokia.com>.";

  description
      "bbf-software-image-managent YANG module supporting
       deviations.
       This specification is published by Nokia under Non-Disclosure
       Agreement(s) (NDA) with specific parties and has to be considered
       as Confidential Information as defined in such NDA. Nokia
       reserves the right to revise this document for any reason,
       including but not limited to conformity with standards
       promulgated by various agencies, utilisation of advances in the
       state of the technical areas, or the reflection of changes in the
       design of any equipment, techniques, or procedures described or
       referred to herein.

       The product specifications and other technical or performance
       information contained herein are subject to change without
       notice. Updates of this document will be issued under the above
       NDA's.

       Nokia makes no representation or warranty, expressed or implied,
       with respect to the sufficiency, accuracy, or utility of any
       information or opinion contained herein. Nokia expressly advises
       that any use of for any purpose or reliance upon this technical
       reference is at the risk of the user and that Nokia shall not be
       liable for any damage or injury incurred by any person arising
       out of the sufficiency, accuracy, or utility of any information
       or opinion contained herein.

       This document is not to be construed as a suggestion to any
       manufacturer to modify or change any of its products, nor does
       this document represent any commitment by Nokia to sell or
       purchase any product. Nothing contained herein shall be construed
       as conferring by implication, estoppel, or otherwise any license
       or right under any patent, whether or not the use of any
       information herein necessarily employs an invention of any
       existing or later issued patent.

       Nokia reserves the right not to offer any or all of these
       products and to withdraw any or all of them at any future time.

       Copyright (C) 2017, Nokia. All Rights Reserved.";

  /* revision */

  revision 2020-07-15 {
     description
       "added new actions and statedata for swm offline migration support in 
        nokia-software-image-management-extension.yang";
     reference
      "Nokia specific"; 
  } 

  revision 2019-05-10 {
    description
      "added leaf server-public-key in
       nokia-software-image-management-extension.yang";
    reference
      "Nokia specific";
  }

  revision 2019-04-23 {
    description
      "Rename and move to swm category.";
    reference
      "TBD";
  }

  revision 2018-11-29 {
    description
      "corrected the errors in comment section in
       bbf-software-image-management-one-dot-one-dev.yang file";
    reference
      "Nokia specific";
  }

  revision 2018-09-21 {
    description
      "added base type as failure-reason to identity no-failure";
    reference
      "TBD";
  }

  revision 2018-08-16 {
    description
      "Initial revision.";
    reference
      "TBD";
  }


/* deviations for length of the URL */
/* -----------------------------*/
/* url is one of the input parameters for */
/* action: download */
/* length of url is restricted to 255 characters */

 deviation "/hw:hardware-state/hw:component/bbf-sim:software/bbf-sim:software/bbf-sim:download/bbf-sim:download-software/bbf-sim:input/bbf-sim:download-method/bbf-sim:url/bbf-sim:url" {
     deviate replace {
       type string {
           length "1..255";
       }
    }
 }

 /* deviations for user provided software name */
 /* -----------------------------------------*/
 /* name is one of the input parameters for */
 /* action: download */
 /* name is restricted to have alphanumeric characters */
 /* and only three special characters "-_." */

 deviation "/hw:hardware-state/hw:component/bbf-sim:software/bbf-sim:software/bbf-sim:download/bbf-sim:download-software/bbf-sim:input/bbf-sim:name" {
    deviate replace {
      type bbf-yang:string-ascii64 {
           pattern '[-a-zA-Z0-9_.]*';
      }
    }
  }

 /* deviations for user provided software name */
 /* -----------------------------------------*/
 /* name is one of the input parameters for */
 /* action: abort */
 /* name is restricted to have alphanumeric characters */
 /* and only three special characters "-_." */

 deviation "/hw:hardware-state/hw:component/bbf-sim:software/bbf-sim:software/bbf-sim:download/bbf-sim:abort-download/bbf-sim:input/bbf-sim:name" {
    deviate replace {
      type bbf-yang:string-ascii64 {
               pattern '[-a-zA-Z0-9_.]*';
      }
    }
  }
}
