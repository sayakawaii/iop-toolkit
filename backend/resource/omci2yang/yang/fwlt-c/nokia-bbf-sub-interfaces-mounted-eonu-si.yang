module nokia-bbf-sub-interfaces-mounted-eonu-si {

  namespace "http://www.nokia.com/Fixed-Networks/BBA/yang/"
           + "nokia-bbf-sub-interfaces-mounted-eonu-si";

  prefix nokia-bbf-sub-interfaces-mounted-eonu-si;

  import bbf-fiber-onu-emulated-mount {
    prefix onu;
  }

  import nokia-sdan-service-impact {
    prefix nokia-si;
  }

  import ietf-interfaces-mounted{
    prefix if-mounted;
  }

  import bbf-sub-interfaces-mounted {
    prefix bbf-subif-mounted;
  }

  organization
    "Nokia";

  contact
    "isam.yang@nokia.com";

  description
    "This module contains a collection of YANG deviations on top
     of standard for supporting BBF/bbf-sub-interfaces-tagging YANG module.
     Copyright (C) 2021, Nokia. All Rights Reserved.";

  revision 2023-06-30 {
    description
      "Initial revision.";
    reference
      "Nokia specific";
  }

  deviation "/onu:onus/onu:onu/onu:root/if-mounted:interfaces/if-mounted:interface/bbf-subif-mounted:subif-lower-layer/bbf-subif-mounted:interface" {
     description
        "When VSI subif-lower-layer interface is modified, traffic will be down for a short time period.
         This will result in service interruptions of several seconds.";
     deviate add {
        nokia-si:service-impact;
      }
  }
}
