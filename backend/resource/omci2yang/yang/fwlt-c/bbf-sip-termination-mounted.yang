submodule bbf-sip-termination-mounted {
  yang-version 1.1;
  belongs-to bbf-sip-voip-mounted  {
    prefix bbf-sip-voip-mounted;
  }
  
  import ietf-inet-types {
    prefix inet;
	reference
      "RFC 6991: Common YANG Data Types.";
  }
  
  import bbf-yang-types {
    prefix bbf-yang;
  }

  import tailf-common {
    prefix tailf;
  }   
   
  include bbf-sip-voip-base-mounted;
  include bbf-sip-types-mounted;
  include bbf-sip-profiles-mounted;
  include bbf-sip-termination-operational-data-mounted;
  include bbf-sip-signaling-notifications-mounted;
  
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains a collection of YANG definitions for
     managing sip pots terminations.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2021-03-24 {
    description
      "Initial rvision.
       * Approval Date:    see revision date above.
       * Publication Date: 2020-03-06.";
    reference
      " ";
  }

  grouping authentication-settings {
    leaf authentication-scheme {
	  type enumeration {
		enum md5-digest {
		  value 1;
		  description
			"The MD5 Digest authentication.";
		} 
		enum aka {
		  value 2;
		  description
		    "The Authentication and key agreement.";
		} 	    
	  }
	  default md5-digest;
	  description
		"Authentication validation scheme for user authentication.";
	}
	leaf realm {
	  type bbf-yang:name-string;
	  description
		"The authentication realm.";
	}
	leaf auth-user-name {
	  type bbf-yang:name-string;
	  description
		"The authentication user name.";
	}
	leaf digest-password {
	when "../bbf-sip-voip-mounted:authentication-scheme ='md5-digest'"; 
	  /* type bbf-yang:name-string; */
	  type tailf:aes-cfb-128-encrypted-string;
	  description
		"The authentication password.";
	}
	leaf aka-secret-key {
	when "../bbf-sip-voip-mounted:authentication-scheme ='aka'"; 
	  type string {length "32";}
	  description
		"The secret key.";	
	}
  }
  
  grouping sip-termination-characteristics {    
	description
	  "The characteristics of the SIP termination.";	  
	leaf global-directory-number {
  	  type string {length "1..32";}
  	  description
		"The global directory number of the SIP user.";
	}
	leaf sip-uni-display-name {
	  type bbf-yang:string-ascii64;			
	  description
		"The display name of the SIP user interface.";
	}			
//	leaf sip-uni-uri-type {
//	  type enumeration {
//		enum sip-uri {
//		  value 1;	      
//		  description
//			"SIP Uniform Resource Identifier.";
//		}
//		enum tel-uri {
//		  value 2;		  
//		  description
//			"TEL Uniform Resource Identifier.";
//		}
//		enum sips-uri {
//		  value 3;		  
//		  description
//		    "SIP Secure Uniform Resource Identifier.";
//		}
//	  }
//	  default sip-uri;			
//	  description
//	    "The SIP uni URI type.";
//	}	
	leaf sip-uni-uri {
	  type inet:uri;			
	  description
		"The SIP  user interface URI.";
	}	  
	leaf sip-uni-pani-header-line-id {
 	  type union {
        type string {length "1..64";}
          type enumeration {
          	enum not-applicable {
			  description
              	"Indicates that pani-header is not applicable.";
			}
		  }
	    }			
	  description
		"The input for this parameter is used to create the 
		 P-Access-Network-Info (PANI) header in the SIP  
		 Register / Invite request. The pani header line id input
		 is not bounded to any format. It is the resonsibility of
		 the customer to define the desired format. There is no 
		 restriction on the character set being used for this 
		 input.";
	}      
    leaf receiver-off-hook-timer {
	  type uint8;
	  units "1 second";
	  default 15;
      description
        "Receiver off hook timer (Roh).";	  
	}
  }  
  
  grouping sip-termination {
    uses authentication-settings;
    uses sip-termination-characteristics;
    leaf sip-uni-suppl-services-profile {
	  /* type bbf-sip-voip-mounted:suppl-services-profile-ref;*/
      type leafref {
        path "../../../../bbf-sip-voip-mounted:sip-profiles"
           + "/bbf-sip-voip-mounted:supplementary-services-profiles"
		   + "/bbf-sip-voip-mounted:supplementary-services-profile"
	       + "/bbf-sip-voip-mounted:name";
      }	  
	  /*default null-pointer;*/			
	  description
		"References the call service profile that applies to the 
		 sip user interface.";
    }	
    leaf sip-uni-digit-manipulation-rule-profile {
// BBOG - this one depends on a feature...
       if-feature bbf-sip-voip-mounted:digit-manipulation;
          type leafref {
              path "../../../../bbf-sip-voip-mounted:sip-profiles"
                + "/bbf-sip-voip-mounted:digit-manipulation-rule-profiles"
                + "/bbf-sip-voip-mounted:digit-manipulation-rule-profile"
                + "/bbf-sip-voip-mounted:name";
          }
	  /*default null-pointer;*/			
	  description
		"References the digit manipulation rule
		 profile that applies to the SIP user interface.";
    }
    //uses sip-termination-operational-data;
    uses sip-termination-notifications;
  }
}
