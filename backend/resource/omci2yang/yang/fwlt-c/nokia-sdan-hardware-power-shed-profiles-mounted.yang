module nokia-sdan-hardware-power-shed-profiles-mounted {
  yang-version 1.1;
  namespace "http://www.nokia.com/Fixed-Networks/BBA/yang/"
             + "nokia-sdan-hardware-power-shed-profiles-mounted";
  prefix nokia-hw-pwr-shed-prof-mounted;

  import bbf-yang-types {
    prefix bbf-yang;
  }

  import bbf-fiber-onu-emulated-mount {
     prefix onu;
  }

  import nokia-template-common {
    prefix template-common;
  }
  
  organization
    "Nokia";

  contact
    "Comments or questions about this Broadband Forum YANG module
     should be directed to <mailto:isam.yang@nokia.com>.";

  description
    "This module contains a collection of YANG definitions for
     power shed profiles for power management.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2023-10-19 {
    description
      "update units from second to seconds.";
    reference
      "";
  }

  revision 2023-10-07 {
    description
      "BBN-5820:it should be a node-actual-usage or node-template-usage ONU 
       for power-shedding-profiles.";
    reference
      "";
  }

  revision 2022-01-18 {
    description
      "Initial revision.";
    reference
      "tbc";
  }

  typedef power-shed-delay-or-disable {
    type union {
      type uint16 {
        range "0 | 2..max";
      } 
      type enumeration {
        enum disable {
          description
            "Disable power shedding";
        }
      }
    }
    units "seconds";
    default disable;
	  description
	  "A type meant for a data node for which a numeric value 
        indicates the delay in seconds before applying power 
        shedding after AC power fails. 
        The enum value 'disable' means that power shedding 
        is not applied after AC power fails. Consistent with this 
        definition, value '0' second means that power shedding must
        immediately be applied after AC power fails. 
        Value '1' second is not allowed because of restriction in 
        ITU-T G.988 clause 9.1.7.";
  }

  augment "/onu:onus/onu:onu/onu:root"{
    when "derived-from-or-self (../onu:usage, 'template-common:node-actual-usage') or
        derived-from-or-self (../onu:usage, 'template-common:node-template-usage')" {
     description
       "it should be a node-actual-usage or node-template-usage ONU for power-shedding-profiles.";
    }
    description "augment onu root with power shedding profiles";
    container power-shedding-profiles {
      description "power shedding profiles";
      list power-shedding-profile {
        key "name";
        description
          "Configuration power shedding profile data nodes";  
        reference 
          "ITU-T G.988 9.1.7 ONU power shedding"; 
        leaf name {
          type bbf-yang:string-ascii64;
          description
            "Indicates name of the profile";
        }
        leaf data-service-power-shed-delay{
          type power-shed-delay-or-disable;
          description
            "Specifies time in seconds before shedding power for
             data service, or disable power shedding for this
             service.";
        }
        leaf voice-service-power-shed-delay{
          type power-shed-delay-or-disable;
          description
            "Specifies time in seconds before shedding power for
             voice service, or disable power shedding for this
             service.";
        }
        leaf video-overlay-service-power-shed-delay{
          type power-shed-delay-or-disable;
          description
            "Specifies time in seconds before shedding power for
             video overlay service, or disable power shedding for this
             service.";
        }
        leaf video-return-service-power-shed-delay{
          type power-shed-delay-or-disable;
          description
            "Specifies time in seconds before shedding power for
             video return service, or disable power shedding for this
             service.";
        }
        leaf dsl-service-power-shed-delay{
          type power-shed-delay-or-disable;
          description
            "Specifies time in seconds before shedding power for
             dsl service, or disable power shedding for this
             service.";
        }
        leaf atm-service-power-shed-delay{
          type power-shed-delay-or-disable;
          description
            "Specifies time in seconds before shedding power for
             atm service, or disable power shedding for this
             service.";
        }
        leaf ces-service-power-shed-delay{
          type power-shed-delay-or-disable;
          description
            "Specifies time in seconds before shedding power for
             ces service, or disable power shedding for this
             service.";
        }
        leaf frame-service-power-shed-delay{
          type power-shed-delay-or-disable;
          description
            "Specifies time in seconds before shedding power for
             frame service, or disable power shedding for this
             service.";
        }
        leaf sdh-sonet-service-power-shed-delay{
          type power-shed-delay-or-disable;
          description
            "Specifies time in seconds before shedding power for
             sdh-sonet service, or disable power shedding for this
             service.";
        }
        leaf power-shed-exit-delay {
          type uint16;
          units "seconds";
          default 0;
          description
            "The time delay, in seconds, before exiting power
             shedding mode after AC power is restored. This delay 
             is the same for all services subjected to power shedding
             capability."; 
        }
      }
    }
  }
}
