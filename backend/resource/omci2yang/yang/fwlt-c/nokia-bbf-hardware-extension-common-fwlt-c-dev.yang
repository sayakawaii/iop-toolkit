module nokia-bbf-hardware-extension-common-fwlt-c-dev {

  namespace
     "http://www.nokia.com/Fixed-Networks/BBA/yang/"
   + "nokia-bbf-hardware-extension-common-fwlt-c-dev";

  prefix nokia-bbf-hardware-extension-common-fwlt-c-dev;

  import ietf-hardware {
    prefix hw;
  }

  import bbf-hardware-extension {
    prefix bbf-hw-ext;
  }

  import iana-hardware {
    prefix ianahw;
  }

  import nokia-hardware-identities {
    prefix nokia-hwi;
  }

  import bbf-hardware-types {
    prefix bbf-hwt;
  }

  organization
    "Nokia";

  contact
    "Comments or questions about this Nokia YANG module should be
     directed to <mailto:isam.yang@nokia.com>.";

  description
    "The NOKIA BBF/hardware YANG module supporting
     deviations on top of standard.";

  revision 2022-02-21 {
    description
      "Added description for eqpt deviations";
    reference
      "BBN-65232";
  }

  revision 2020-03-18 {
    description
      "Efficient autogenerated hw deviations";
    reference
      "Nokia specific";
  }

  deviation "/hw:hardware/hw:component/bbf-hw-ext:model-name" {
    deviate add {
      must "
        (current()/../hw:class = 'bbf-hwt:transceiver' and (
          (
            (
              substring(current(), 1, 8) = '3FE53441' or
              current() = 'NOKIA_GPON' or
              current() = 'NON_NOKIA_GPON'
            )
            and (not(boolean(/hw:hardware/hw:component[hw:parent = current()/../hw:name]
                                                      [hw:class != 'nokia-hwi:transceiver-link-gpon']
              )))
          )
          or (
            (
              substring(current(), 1, 8) = '3FE47548' or
              substring(current(), 1, 8) = '3FE48234' or
              current() = 'NOKIA_NGPON' or
              current() = 'NON_NOKIA_NGPON'
            )
            and (not(boolean(/hw:hardware/hw:component[hw:parent = current()/../hw:name]
                                                      [hw:class != 'nokia-hwi:transceiver-link-ngpon']
              )))
          )
          or (
            (
              substring(current(), 1, 8) = '3FE66606' or
              substring(current(), 1, 8) = '3FE47581' or
              substring(current(), 1, 8) = '3FE49128' or
              current() = 'NOKIA_MPM'
            )
            and (not(boolean(/hw:hardware/hw:component[hw:parent = current()/../hw:name]
                                                      [hw:class = 'nokia-hwi:transceiver-link-twentyfivegspon']
              )))
          )
          or (
            (
              substring(current(), 1, 8) = '3FE48259' or
              substring(current(), 1, 8) = '3FE49650' or
              current() = 'NOKIA_25GSPON'
            )
            and (not(boolean(/hw:hardware/hw:component[hw:parent = current()/../hw:name]
                                                      [hw:class != 'nokia-hwi:transceiver-link-twentyfivegspon']
              )))
          )
        ))
        or
        (current()/../hw:class = 'nokia-hwi:lt' and (
          (
            (
              current() = 'FWLT-C'
            )
          )
        ))
        or
        (current()/../hw:class = 'ianahw:chassis' and (
          (
            (
              substring(current(), 1, 0) = ''
            )
          )
        ))
        "
      {
        error-message "Invalid model type or too many hardware components configured for specific model type.";
        description "Invalid model type or too many hardware components configured for specific model type,
        e.g. the class type of the transceiver-link is not allowed for the model-name 'NOKIA_ELECTRICAL' of its parent transceiver";
      }
    }
  }
}
