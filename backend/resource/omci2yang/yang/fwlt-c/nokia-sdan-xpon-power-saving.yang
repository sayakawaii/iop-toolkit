module nokia-sdan-xpon-power-saving {
  yang-version 1.1;
  namespace "http://www.nokia.com/Fixed-Networks/BBA/yang/"
  + "nokia-sdan-xpon-power-saving";

  prefix nokia-sdan-xpon-ps;

  import ietf-hardware {
    prefix hw;
  }

  import bbf-hardware-types {
    prefix bbf-hwt;
  }

  import nokia-sdan-power-saving {
    prefix nokia-sdan-ps;
  }

  import nokia-sdan-xpon-power-saving-common {
    prefix nokia-sdan-xpon-pwr-savc;
  }

  organization
    "Nokia";

  contact
    "Comments or questions about this Nokia YANG module should be
     directed to <mailto:isam.yang@nokia.com>.";

  description
    "This module contains a collection of YANG definitions for
     supporting Nokia specific requirements as applicable to its
     access network equipment.

     Specifically, this module models data to manage xPON power
     saving in the OLT, such as power saving on xPON transceivers
     and transceiver links, using various criteria.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
     Nokia reserves the right not to offer any or all of these
     products and to withdraw any or all of them at any future time.
     Copyright (C) 2025, Nokia. All Rights Reserved.";

  revision 2025-05-30 {
    description
      "Initial version of the power saving module
       to model the data to manage xPON transceiver
       power-saving on OLT";
    reference
      "Nokia specific";
  }

  augment "/nokia-sdan-ps:power-saving" {
    if-feature nokia-sdan-xpon-pwr-savc:xpon-transceiver-power-saving;
    description
      "Augments system power saving configuration with xPON
       transceiver power saving data nodes.";

    container xpon-transceiver {
      presence
        "Presence of this container indicates that global xPON
         transceiver power saving control is supported on this OLT.";
      description
        "xPON transceiver power saving configuration data nodes.";
      uses nokia-sdan-xpon-pwr-savc:power-saving-xpon-transceiver-config-data;
    }
  }

  augment "/hw:hardware/hw:component/nokia-sdan-ps:power-saving" {
    when "derived-from-or-self(../hw:class,'bbf-hwt:transceiver')" {
      description
        "This augment is only applicable for a transceiver.";
    }
    if-feature nokia-sdan-xpon-pwr-savc:xpon-transceiver-power-saving;
    description
      "Augments specific xPON transceivers with power saving
       configurations. Configuration at this level overrules any
       power saving data configured at the system level for xPON
       transceivers. The data nodes of this augment are only
       relevant for transceivers used for xPON. It they are
       configured for a transceiver not used fof xPON, they will
       be silently ignored.";
    uses nokia-sdan-xpon-pwr-savc:power-saving-xpon-transceiver-config-data;
  }

  augment "/hw:hardware-state/hw:component/nokia-sdan-ps:power-saving/"
         + "nokia-sdan-ps:state" {
    when "derived-from-or-self(../../hw:class,'bbf-hwt:transceiver')
          or derived-from-or-self(../../hw:class,
          'bbf-hwt:transceiver-link')" {
      description
        "This augment is only applicable for xPON transceiver or
         transceiver-links.";
    }
    if-feature nokia-sdan-xpon-pwr-savc:xpon-transceiver-power-saving;
    description
      "Augments hardware component with xPON transceiver power saving
       state data.";
    leaf-list applied-xpon-criteria {
      type identityref {
        base nokia-sdan-xpon-pwr-savc:power-saving-xpon-transceiver-criteria;
      }
      description
        "State data node showing which power saving criteria is
         currently met for this hardware component.";
    }
  }
}
