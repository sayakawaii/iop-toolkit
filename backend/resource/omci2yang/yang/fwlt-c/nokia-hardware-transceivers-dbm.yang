module nokia-hardware-transceivers-dbm {
  yang-version 1.1;

  namespace "http://www.nokia.com/Fixed-Networks/BBA/yang/"
  + "nokia-hardware-transceivers-dbm";

  prefix nokia-hw-xcvr-dbm;

  import ietf-hardware {
    prefix hw;
  }
  import bbf-hardware-transceivers {
    prefix bbf-hw-xcvr;
  }

  organization
    "Nokia";

  contact
     "Comments or questions about this Nokia YANG module should be
     directed to <mailto:isam.yang@nokia.com>.";


  description
     "This module contains a collection of YANG definitions for
     supporting Nokia specific requirements as applicable to its
     access network equipment.

     Specifically, this module augments the hardware model with
	 additional identifying operational data of a component.
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2021-03-17 {
       description
         "Support transceiver rx-power and tx-power in 0.1dBm Units";
       reference
         "Nokia specific.EPIC BBN-1693";
  }

  augment "/hw:hardware-state/hw:component/bbf-hw-xcvr:transceiver-link/bbf-hw-xcvr:diagnostics" {
    description
      "Augment the transceiver-link hardware state with NOKIA specific rssi threshold values.";

      leaf tx-power-dbm {
        type int16;
        units "0.1 dBm";
        description
          "Measured TX output power in dBm. Data is assumed to be
           based on measurement of laser monitor photodiode current.
           It is factory calibrated to absolute units using the most
           representative fiber output type. Accuracy is vendor
           specific but must be better than +/- 3dB over specified
           temperature and voltage.";
        reference
          "SFF-8472 Revision 12.3, Section 9.7 - Byte 102-103";
      }

      leaf rx-power-dbm {
        type int16;
        units "0.1 dBm";
        description
          "Measured received (RX) optical power in dBm. Absolute
           accuracy is dependent upon the exact optical wavelength.
           For the vendor specified wavelength, accuracy shall be
           better than +/- 3dB over specified temperature and
           voltage. This accuracy shall be maintained for input
           power levels up to the lesser of maximum transmitted or
           maximum received optical power per the appropriate
           standard. It shall be maintained down to the minimum
           transmitted power minus cable plant loss (insertion  loss
           or passive loss) per the appropriate standard. Absolute
           accuracy beyond this minimum required received input
           optical power range is vendor specific.";
        reference
          "SFF-8472 Revision 12.3, Section 9.7 - Byte 104-105";
      }
  }
}
