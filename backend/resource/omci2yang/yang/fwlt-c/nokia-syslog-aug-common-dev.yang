module nokia-syslog-aug-common-dev {

    yang-version 1.1;

    namespace
        "http://www.nokia.com/Fixed-Networks/BBA/yang/nokia-syslog-aug-common-dev";

    prefix nokia-syslog-aug-common-dev;

    import ietf-syslog {
        prefix syslog;
    }

    import nokia-syslog-aug {
        prefix syslog-aug;
    }

    organization
        "Nokia";

    contact
      "Comments or questions about this Nokia YANG module should be
       directed to <mailto:isam.yang@nokia.com>.";

    description
      "This module contains a collection of YANG definitions for
       supporting Nokia specific requirements as applicable to its
       access network equipment.

       Specifically, this module identifies data that potentially
       contains private data. Note that this classification is product
       independent while the support of this data is product dependent.
       I.e. it might be that data that is identified as private is not
       supported in a particular product variant.

       This specification is published by Nokia under Non-Disclosure
       Agreement(s) (NDA) with specific parties and has to be considered
       as Confidential Information as defined in such NDA. Nokia
       reserves the right to revise this document for any reason,
       including but not limited to conformity with standards
       promulgated by various agencies, utilisation of advances in the
       state of the technical areas, or the reflection of changes in the
       design of any equipment, techniques, or procedures described or
       referred to herein.

       The product specifications and other technical or performance
       information contained herein are subject to change without
       notice. Updates of this document will be issued under the above
       NDA's.

       Nokia makes no representation or warranty, expressed or implied,
       with respect to the sufficiency, accuracy, or utility of any
       information or opinion contained herein. Nokia expressly advises
       that any use of for any purpose or reliance upon this technical
       reference is at the risk of the user and that Nokia shall not be
       liable for any damage or injury incurred by any person arising
       out of the sufficiency, accuracy, or utility of any information
       or opinion contained herein.

       This document is not to be construed as a suggestion to any
       manufacturer to modify or change any of its products, nor does
       this document represent any commitment by Nokia to sell or
       purchase any product. Nothing contained herein shall be construed
       as conferring by implication, estoppel, or otherwise any license
       or right under any patent, whether or not the use of any
       information herein necessarily employs an invention of any
       existing or later issued patent.

       Nokia reserves the right not to offer any or all of these
       products and to withdraw any or all of them at any future time.

       Copyright (C) 2021, Nokia. All Rights Reserved.";

    revision 2025-07-27 {
     description "Ensure mutual exclusivity for est-certificate-profile and pinned-ca-certs";
     reference "Nokia Specific";
    }

    revision 2023-06-09 {
     description "YANG lint error fixes";
     reference "Nokia specific";
    }

    revision 2021-07-17 {
     description
      "Adding proper descriptions and error messages to deviations.";
      reference "Nokia specific";
    }

    revision 2021-07-08 {
     description
      "Facility list and pattern match cannot be configured
       if there is no file name given";
     reference "Nokia Specific";
    }

    deviation "/syslog:syslog/syslog-aug:verbose/syslog-aug:file/syslog-aug:facility-filter/syslog-aug:facility-list" {
        deviate add {
            must "(current()/../../syslog-aug:name)" {
                error-message "File name is empty - Please give a file name";
                description "In order to be able to configure the desired facility/severity, file name must be configured.";
            }
        }
    }

    deviation "/syslog:syslog/syslog-aug:verbose/syslog-aug:file/syslog-aug:pattern-match" {
        deviate add {
            must "(current()/../syslog-aug:name)" {
                error-message "File name is empty - Please give a file name";
                description "In order to be able to configure the desired pattern-match, file name must be configured.";
            }
        }
    }


    deviation "/syslog:syslog/syslog:actions/syslog:remote/syslog:destination/syslog:transport/syslog:tls/syslog:tls/syslog:server-auth/syslog-aug:est-certificate-profile" {
        deviate add {
            must "boolean(current()) != boolean(../syslog:pinned-ca-certs)" {
                error-message "'est-certificate-profile' and 'pinned-ca-certs' cannot both be set at the same time.";
                description "This constraint ensures that exactly one of 'est-certificate-profile' or 'pinned-ca-certs' is set, but not both.";
            }
        }
    }

    deviation "/syslog:syslog/syslog:actions/syslog:remote/syslog:destination/syslog:transport/syslog:tls/syslog:tls/syslog:client-identity/syslog:auth-type/syslog:certificate/syslog:certificate/syslog:local-or-keystore/syslog:keystore/syslog-aug:certificate-reference-choice/syslog-aug:central-keystore-reference/syslog-aug:central-keystore-reference/syslog-aug:asymmetric-key" {
         deviate add {
            must "../syslog-aug:certificate" {
                error-message "'asymmetric-key' must be configured together with 'certificate' under 'central-keystore-reference'";
                description "'asymmetric-key' must be configured together with 'certificate' under 'central-keystore-reference'.";
            }
         }
    }



}
