module ietf-system-frommounted {
    yang-version "1.1";
    namespace "urn:ietf:params:xml:ns:yang:ietf-system-frommounted";
    prefix "sys-frommounted";

    import ietf-inet-types {
      prefix inet;
    }

    import bbf-fiber-onu-emulated-mount {
      prefix onu;
    }


    organization
      "IETF NETMOD (NETCONF Data Modeling Language) Working Group";

    contact
      "WG Web:   <http://tools.ietf.org/wg/netmod/>
       WG List:  <mailto:netmod@ietf.org>

       WG Chair: Thomas Nadeau
                 <mailto:tnadeau@lucidvision.com>

       WG Chair: Juergen Schoenwaelder
                 <mailto:j.schoenwaelder@jacobs-university.de>

       Editor:   Andy Bierman
                 <mailto:andy@yumaworks.com>

       Editor:   Martin Bjorklund
                 <mailto:mbj@tail-f.com>";

    description
      "This module contains a collection of YANG definitions for the
       configuration and identification of some common system
       properties within a device containing a NETCONF server.  This
       includes data node definitions for system identification,
       time-of-day management, user management, DNS resolver
       configuration, and some protocol operations for system
       management.

       Copyright (c) 2014 IETF Trust and the persons identified as
       authors of the code.  All rights reserved.

       Redistribution and use in source and binary forms, with or
       without modification, is permitted pursuant to, and subject
       to the license terms contained in, the Simplified BSD License
       set forth in Section 4.c of the IETF Trust's Legal Provisions
       Relating to IETF Documents
       (http://trustee.ietf.org/license-info).

       This version of this YANG module is part of RFC 7317; see
       the RFC itself for full legal notices.";

    revision 2022-02-11 {
      description
        "Updated to replace RPC by actions.";
      reference
        "RFC7950 Schema Mount";
    }
    
    revision 2014-08-06 {
      description
        "Initial revision.";
      reference
        "RFC 7317: A YANG Data Model for System Management";
    }

   /*
    * Typedefs
    */

    typedef timezone-name {
      type string;
      description
        "A time zone name as used by the Time Zone Database,
         sometimes referred to as the 'Olson Database'.

         The exact set of valid values is an implementation-specific
         matter.  Client discovery of the exact set of time zone names
         for a particular server is out of scope.";
      reference
        "RFC 6557: Procedures for Maintaining the Time Zone Database";
     }


    /*
     * Identities
     */

    identity authentication-method {
      description
        "Base identity for user authentication methods.";
    }

    identity radius {
      base authentication-method;
      description
        "Indicates user authentication using RADIUS.";
      reference
        "RFC 2865: Remote Authentication Dial In User Service (RADIUS)
         RFC 5607: Remote Authentication Dial-In User Service (RADIUS)
                   Authorization for Network Access Server (NAS)
                   Management";
    }

    identity local-users {
      base authentication-method;
      description
        "Indicates password-based authentication of locally
         configured users.";
    }

    identity radius-authentication-type {
      description
        "Base identity for RADIUS authentication types.";
    }

    identity radius-pap {
      base radius-authentication-type;
      description
        "The device requests Password Authentication Protocol (PAP)
         authentication from the RADIUS server.";
      reference
        "RFC 2865: Remote Authentication Dial In User Service (RADIUS)";
    }

    identity radius-chap {
      base radius-authentication-type;
      description
        "The device requests Challenge Handshake Authentication
         Protocol (CHAP) authentication from the RADIUS server.";
      reference
        "RFC 2865: Remote Authentication Dial In User Service (RADIUS)";
    }

    /*
     * Configuration data nodes
     */
augment '/onu:onus/onu:onu/onu:fromroot' {
      container system {
        presence "system";
        description
          "System group configuration.";
        container clock {
          presence "clock";
          description
            "Configuration of the system date and time properties.";

          choice timezone {
            description
              "The system time zone information.";

            case timezone-name {
              leaf timezone-name {
                type timezone-name;
                description
                  "The TZ database name to use for the system, such
                  as 'Europe/Stockholm'.";
              }
            }
            case timezone-utc-offset {
              leaf timezone-utc-offset {
                type int16 {
                  range "-1500 .. 1500";
                }
                units "minutes";
                description
                  "The number of minutes to add to UTC time to
                  identify the time zone for this system.  For example,
                  'UTC - 8:00 hours' would be represented as '-480'.
                  Note that automatic daylight saving time adjustment
                  is not provided if this object is used.";
              }
            }
          }
        }

        container dns-resolver {
          presence "dns-resolver";
          description
            "Configuration of the DNS resolver.";

          list server {
            key name;
            ordered-by user;
            description
              "List of the DNS servers that the resolver should query.

              When the resolver is invoked by a calling application, it
              sends the query to the first name server in this list.  If
              no response has been received within 'timeout' seconds,
              the resolver continues with the next server in the list.
              If no response is received from any server, the resolver
              continues with the first server again.  When the resolver
              has traversed the list 'attempts' times without receiving
              any response, it gives up and returns an error to the
              calling application.

              Implementations MAY limit the number of entries in this
              list.";

            leaf name {
              type string;
              description
                "An arbitrary name for the DNS server.";
            }
            choice transport {
              description
                "The transport-protocol-specific parameters for this
                server.";

              case udp-and-tcp {
                container udp-and-tcp {
                  presence "udp-and-tcp";
                  description
                    "Contains UDP- and TCP-specific configuration
                    parameters for DNS.";
                  reference
                    "RFC 1035: Domain Names - Implementation and
                              Specification
                    RFC 5966: DNS Transport over TCP - Implementation
                              Requirements";

                  leaf address {
                    type inet:ipv4-address-no-zone;
                    description
                      "The address of the DNS server.";
                  }
                }
              }
            }
          }
        }

      }
    }
    

  }
