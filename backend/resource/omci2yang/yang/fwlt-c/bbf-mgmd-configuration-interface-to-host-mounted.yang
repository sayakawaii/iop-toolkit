submodule bbf-mgmd-configuration-interface-to-host-mounted {
  yang-version 1.1;
  belongs-to bbf-mgmd-mounted {
    prefix bbf-mgmd-c-i2h-mounted;
  }

  organization
    "Broadband Forum <https://www.broadband-forum.org>
     Common YANG Project Stream";

  contact
    "Comments or questions about this Broadband Forum YANG module
     should be directed to <mailto:help@broadband-forum.org>.

     Editor:      Joey Boyd, ADTRAN
                  <mailto:joey.boyd@adtran.com>

     Editor:      Ludwig Pauwels, Nokia
                  <mailto:ludwig.pauwels@nokia.com>

     PS Leader:   Michael Shaffer, Nokia
                  <mailto:michael.shaffer@nokia.com>

     PS Leader:   William Lupton, Broadband Forum
                  <mailto:wlupton@broadband-forum.org>";

  description
    "This module contains a collection of YANG definitions for 
     supporting the Multicast Group Membership Discovery (MGMD) 
     Protocols. In particular, it describes configuration objects used
     for managing the Internet Group Management Protocol (IGMP) and 
     the Multicast Listener Discovery (MLD) protocol on interfaces 
     that connect the system to multicast hosts.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2018-03-28 {
    description
      "Initial revision.
       * Approval Date:    see revision date above.
       * Publication Date: yyyy-mm-dd.";
    reference
      "TR-383: Common YANG Modules
               <https://www.broadband-forum.org/technical/download/
                        TR-383.pdf>";
  }

  grouping interface-to-host {
    description
      "Grouping of objects used for configuring the Internet Group 
       Management Protocol (IGMP) and the Multicast Listener Discovery
       (MLD) protocol on interfaces that connect multicast hosts.";

    leaf query-interval {
      type uint32 {
        range "1..31744";
      }
      units seconds;
      default "125";
      description
        "The interval at which MGMD general membership query messages 
        (GMQs) are sent on interfaces.";
      reference
        "RFC 3376 Section 8.2;
         RFC 3810 Section 9.14.2;
         RFC 5519 mgmdRouterInterfaceQueryInterval";
    }

    leaf query-max-response-time {
      type uint32 {
        range "0..31744";
      }
      units "0.1 seconds";
      default "100";
      description
        "The maximum query response time advertised in MGMD general 
         query messages sent on interfaces. The value 0 means that the
         host receiving the query shall reply immediately on it. A 
         value different than 0 means that the host waits a random 
         time between 0 and the time specified in the query message 
         before answering the query.

         The object is shared between IGMPv2, MLDv1, IGMPv3 and MLDv2 
         but has a difference in translating the configured value into
         a time inserted in the query message:

         IGMPv2:
           Object value < 255 : the time value is equal to the object 
           value (units in 100ms)
           Object value >= 255 : the time value is 255 (units in 
           100ms)
        
         MLDv1:
           Object value < 374 : the time value is equal to the object 
           value (units in 100ms)
           Object value >= 374 : the time value is 374 (units in
           100ms)
        
         IGMPv3 & MLDv2:
           Object value < 128 : the time value is equal to the object
           value (units in 100ms)
           Object value >= 128 : the time value is calculated from the
           object value. It is the lowest discrete value higher or 
           equal to the object value.
           The supported set of discrete values are calculated from a 
           floating point calculation 'mantissa * (2 power(exponent))'
           for which the mantissa is a number from 16 to 31 and the 
           exponent is a number from 3 to 10.";           
      reference
        "RFC 2710 section 7.3;
         RFC 2933 igmpInterfaceQueryMaxResponseTime;
         RFC 3376 Section 8.3;
         RFC 3810 Section 5.1.9;
         RFC 5519 mgmdRouterInterfaceQueryMaxResponseTime";
    }

    leaf last-member-query-interval {
      when '../immediate-leave = "disabled"';
      type uint32 {
        range "2..31744";
      }
      units "0.1 seconds";
      default "10";
      description
        "The last member query interval is the max response time
         inserted into group-specific query messages sent in response
         to leave group messages, and is also the amount of time 
         between group-specific query messages.";
      reference
        "RFC 2710 section 7.8;
         RFC3376 Section 8.8;
         RFC5519 mgmdRouterInterfaceLastMemberQueryInterval";
    }

    leaf last-member-query-count {
      when '../immediate-leave = "disabled"';
      type uint32 {
        range "1..255";
      }
      default "2";
      description
        "The number of unanswered Group Specific Queries sent out
         before it is assumed that there are no local members
         interested in the IP multicast stream.

         This object is applied to each interfaces on which the proxy 
         generates Queries.";
      reference
        "RFC3376 Section 8.9";
    }
    
    leaf startup-query-interval {
      type uint32 {
        range "0..31744";
      }
      units "seconds";
      default "30";
      description
        "This variable represents the interval between General Queries
         sent by a Querier on startup.";
      reference
        "RFC3376 Section 8.6";
    }

    leaf startup-query-count {
      type uint32 {
        range "1..255";
      }
      default "2";
      description
        "The Startup Query Count is the number of General Queries sent
         out on startup, separated by the Startup Query Interval.";
      reference
        "RFC3376 Section 8.7";
    }

    leaf immediate-leave {
      type enumeration {
        enum "enabled" {
          description
            "Enabled";
        }
        enum "disabled" {
          description
            "Disabled";
        }
      }
      default "disabled";
      description
        "Immediate leave controls the function by which an interface 
         that receives a leave group message for a certain group might
         immediately delete the corresponding group record.

         Configuring immediate leave reduces the amount of time it
         takes for the switch to stop sending multicast traffic to an 
         interface when the last host on that interface leaves the 
         group.

         When immediate leave is disabled, the switch no longer tracks
         hosts. Instead, whenever it receives a leave group from a 
         host on an interface, it sends out a group-specific query to 
         all hosts on that interface. If it does not receive any 
         membership reports on the interface in response to the 
         group-specific query within a set interval, it stops 
         forwarding multicast traffic to the interface.";
      reference
        "G.988 Section 9.3.27 Immediate Leave";
    }

    leaf robustness {
      type uint32 {
        range "1..255";
      }
      default "2";
      description
        "The robustness variable allows tuning for the expected packet
         loss on a subnet. If a subnet is expected to be lossy, the
         robustness variable may be increased. IGMP and MLD are robust
         to (robustness variable - 1) packet losses.";
      reference
        "RFC 3376 Section 8.1;
         RFC 5519 mgmdRouterInterfaceRobustness";
    }
  }
}
