module nokia-syslog-aug {
  yang-version 1.1;
  namespace "http://www.nokia.com/Fixed-Networks/BBA/yang/"
    + "nokia-syslog-aug";

  prefix syslog-aug;

  import ietf-syslog {
    prefix syslog;
  }

  import ietf-tcp-common {
    prefix tcpcmn;
  }

  import nokia-sdan-keystore-types {
    prefix nokia-ks;
  }
  import nokia-sdan-est-client { prefix estc; }

  organization
    "Nokia";

  contact
    "Comments or questions about this Nokia YANG module should be
     directed to <mailto:isam.yang@nokia.com>.";

  description
    "This module contains a collection of YANG definitions for
     supporting Nokia specific requirements as applicable to its
     access network equipment.

     Specifically, this module augments the ietf-ipfix-psamp model
     with additional configuration and operational data. Some
     of them specific to IPFIX tcpExporter in fallback mode.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2026-01-23 {
    description "Introduce time-format and increase max remote destinations";
    reference "Nokia specific";
  }

  revision 2025-05-27 {
    description "EST support";
    reference "Nokia specific";
  }

  revision 2024-05-30 {
    description "Keystore container addition";
    reference "Nokia specific";
  }

  revision 2023-09-06 {
    description
    "TLS Keepalive values addition";
    reference
    "Nokia specific";
  }

  revision 2023-04-21 {
    description
    "YANG error fixes";
    reference
    "Nokia specific";
  }

    revision 2021-06-29 {
    description
      "Reduce the max number of files from 10 to 5
      and add descriptions";
    reference
	"Nokia Specific.";
    }

  revision 2021-04-01 {
    description
      "Added internal log file for verbose tracing";
    reference
	"Nokia Specific.";
  }

  augment '/syslog:syslog' {
    description
      "Augments syslog configuration container for introducing internal syslog file.";
    container verbose {
      description
          "Configuration of syslog verbose tracing file";
      container file {
        description
          "This container describes the configuration parameters for
           logging internal logs.";
        leaf name {
          type string {
            length "1 .. 31";
            pattern '[0-9a-zA-Z\-_]+(\.)?[0-9a-zA-Z\-_]*';
          }
          description
            "This leaf specifies the name of the log file.";
        }
        uses syslog:selector;
        container file-rotation {
	        when "../name" {
            description
              "Name must be configured in order to configure
               file-rotation parameters";
          }
          description
            "This container describes the configuration
             parameters for log file rotation.";
          leaf number-of-files {
            type uint32 {
              range "1..5";
            }
            default 1;
            description
               "This leaf specifies the maximum number
                of rotated log files";
          }
          leaf max-file-size {
            type uint32 {
              range "1..3";
            }
            units "megabytes";
            default 1;
            description
              "This leaf specifies the maximum log file size.";
          }
          leaf rollover {
            type uint32 {
              range "60 | 1440 | 10080";
            }
            units "minutes";
            description
              "This leaf specifies the length of time that log
              events should be written to a specific log file.
              Log events that arrive after the rollover period
              cause the current log file to be closed and a new
              log file to be opened. Values must be in minutes and
              could be either 60(hourly), 1440(daily), 10.080(weekly).";
          }
          leaf retention {
            type uint32 {
              range "24 | 168 | 720";
            }
            units "hours";
            description
              "This leaf specifies the length of time that
              completed/closed log event files should be stored
              in the file system before they are deleted. Values
              must be in hours and could be either 24 (daily), 168
              (7*24 weekly), 720 (30*24 monthly)";
          }
        }
      }
    }
  }
  augment '/syslog:syslog/syslog:actions/syslog:remote/syslog:destination/syslog:transport/syslog:tls/syslog:tls' {
    description "Augments syslog tls configuration container for introducing tcp-common-grouping.";
    uses tcpcmn:tcp-common-grouping;
  }

  augment '/syslog:syslog/syslog:actions/syslog:remote/syslog:destination' {
    description "Augments syslog tls configuration container for introducing time-format options.";
      leaf time-format {
        type enumeration {
          enum "utc" {
            description
              "Messages use UTC (Coordinated Universal Time) format with timezone indicator 'Z'.";
          }
          enum "local-time" {
            description
              "Messages use local system time with timezone offset (e.g., +02:00 or -05:00).";
          }
        }
        default "utc";
        description
          "This leaf specifies the time format to be used in syslog message timestamps.";
      }
  }

  augment "/syslog:syslog/syslog:actions/syslog:remote/syslog:destination/syslog:transport/syslog:tls/syslog:tls/syslog:server-auth" {
        description "Augments CA certificate configuration with a reference to an EST CA certificate profile";
        uses estc:est-ca-certificate-profile-ref-grouping;
  }

  augment "/syslog:syslog/syslog:actions/syslog:remote/syslog:destination/syslog:transport/syslog:tls/syslog:tls/syslog:client-identity/syslog:auth-type/syslog:certificate/syslog:certificate/syslog:local-or-keystore/syslog:keystore" {
    description "Augments syslog tls keystore configuration container for introducing asymmetric-key-certificate-ref-grouping.";

    choice certificate-reference-choice {
        description "Choice between a central keystore reference and an EST certificate profile";

        case central-keystore-reference {
            container central-keystore-reference {
                uses nokia-ks:asymmetric-key-certificate-ref-grouping;
                description "A reference to a specific certificate associated with an asymmetric key stored in the central keystore.";
            }
        }

        case est-certificate-profile-reference {
            container est-certificate-profile-reference {
                uses estc:est-certificate-profile-ref-grouping;
                description "Reference to an EST certificate profile for TLS identity configuration.";
            }
        }
    }
  }





}
