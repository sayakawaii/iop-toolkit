module nokia-sdan-xpon-access-line-characteristics-dhcpv4 {
  yang-version 1.1;
  namespace "http://www.nokia.com/Fixed-Networks/BBA/yang/"
          + "nokia-sdan-xpon-access-line-characteristics-dhcpv4";
  prefix nokia-xpon-acc-dr4;

  import bbf-l2-dhcpv4-relay {
    prefix bbf-l2-d4r;
  }

  import bbf-xpon-access-line-characteristics-type {
    prefix bbf-xpon-acc-type;
  }

  organization
    "Nokia";

  contact
    "Comments or questions about this Nokia YANG module should be
     directed to <mailto:isam.yang@nokia.com>.";

  description
    "This module contains a collection of YANG definitions for
     supporting Nokia specific requirements as applicable to its
     access network equipment.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2026, Nokia. All Rights Reserved.";

  revision 2026-06-05 {
    description
      "Initial revision.";
    reference
      "Nokia specific";
  }

  grouping xpon-access-line-characteristics-config-parameters-dhcpv4 {
    description
      "Defines the configuration of xPON access line characteristics to be
       included in vendor specific sub option.";
      leaf-list xpon-access-loop-characteristics {
	type identityref {
	  base bbf-xpon-acc-type:xpon-access-line-attribute-dhcpv4;
	}
	description
	  "An access line characteristics to be included in the protocol frames
	   vendor specific tag. If the list is empty the xPON-Access-Line-characteristics
	   TLV will not be sent.";

	reference
	  "IETF 'draft-lihawi-ancp-protocol-access-extension-03' clause 6.3";
      }
  }

  augment
    "/bbf-l2-d4r:l2-dhcpv4-relay-profiles" +
    "/bbf-l2-d4r:l2-dhcpv4-relay-profile" +
    "/bbf-l2-d4r:option82-format" {
    description
      "Augments the configuration of the DHCPv4 relay profile with
       additional xPON line characteristics configuration.";

      uses xpon-access-line-characteristics-config-parameters-dhcpv4;
  }
}
