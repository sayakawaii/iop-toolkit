module nokia-sdan-onu-configuration-errors-mounted {
  yang-version 1.1;
  namespace "http://www.nokia.com/Fixed-Networks/BBA/yang/"+
            "nokia-sdan-onu-configuration-errors-mounted";
  prefix nokia-onu-config-err-mounted;

  import ietf-yang-types {
    prefix yang;
  }

  import bbf-fiber-onu-emulated-mount {
     prefix onu;
  }

  organization
    "Nokia";
  contact
    "Comments or questions about this Nokia YANG module should be
     directed to <mailto:isam.yang@nokia.com>.";
  description
    "This module contains a collection of YANG definitions for
     supporting Nokia specific requirements as applicable to its
     access network equipment.

     Specifically, this module contains a collection of YANG definitions
     to provide sufficient troubleshooting information for the configuration
     errors occurred during configuration transactions.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2022-09-03 {
    description
      "Initial revision.";
    reference "Nokia specific";
  }

  augment "/onu:onus/onu:onu/onu:root" {
      description "augment onu root with config errors";
      container onu-configuration-errors {
        config false;
        description
          "Configuration error state data";
        list error {
          key "error-number";
          description
            "This list reports ONU state data about OMCI errors encountered
            when configuring an ONU once it is authenticated. Since it is ONU state data,
            an entry in this list will be removed when the corresponding ONU is not 'present'
            any more for instance because it is disconnected, powered-off or rebooted. In case
            the list reaches maximum size, it will stop recording ONU configuration errors";
          leaf error-number {
            type uint16;
            description
              "The ordered number of the configuration error encountered";
          }
          leaf xpath {
            type instance-identifier {
              require-instance false;
            }
            description
              "The xpath where the configuration error encountered";
          }
          leaf error-description {
            type string;
            description
              "The description of the configuration error encountered";
          }
          container omci {
            description
              "Additional OMCI protocol related items assuming configuration error due to omci error response";
            leaf omci-msg-type {
              type string;
              description
                "The OMCI messgae type (e.g. Create, Set, Delete) where the configuration error encountered";
            }
            leaf me-class-name {
              type string;
              description
                "The OMCI ME name (e.g. ANI-G) where the configuration error encountered";
            }
          }
          leaf time {
            type yang:date-and-time;
            description
              "The time when the configuration error was encountered";
          }
        }
      }
    }
}
