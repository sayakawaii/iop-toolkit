module nokia-sdan-ext-aaa-aug {
  yang-version "1.1";
  namespace
    "http://www.nokia.com/Fixed-Networks/BBA/yang/nokia-sdan-ext-aaa-aug";

  prefix nokia-ext-aaa;

  import ietf-system {
    prefix sys;
  }

  import nokia-radius-operator-auth {
    prefix nokia-radius-oper-auth;
  }

  organization
    "Nokia";

  contact
    "isam.yang@nokia.com";

  description
    "The NOKIA IETF/System YANG module supporting
     deviations on top of standard.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2023, Nokia. All Rights Reserved.";

  revision 2023-03-24 {
    description "Remove if-feature nokia-radius-oper-auth:radius-operator-auth";
    reference "BBN-39109";
  }

  revision 2023-03-14 {
    description "Enable operator users auth. via RADIUS server.";
    reference "BBN-39109";
  }

  feature external-authentication {
      description "External authentication for operator users can be enabled on board.";
  }

  augment "/sys:system" {
    description
      "Configuration of external authentication for operator users on system level.";
    container external-user-authentication {
      if-feature external-authentication;
      description
          "Enables external authentication of operator users.";
      container radius {
        when '/sys:system/sys:radius/nokia-radius-oper-auth:operator-auth/nokia-radius-oper-auth:cli-session-policy' {
          description
            "The RADIUS server must be configured before activating external authentication.";
        }
        presence "Enables authentication, authorization of operator users via RADIUS";
        description
          "Define on system level, if authentication and authorization of operator users
          via RADIUS server is allowed.";
        container cli {
          presence
              "If present, external authentication of operator users for CLI sessions is activated.";
          description
            "Enables external authentication of operator users for CLI sessions.";
          leaf auth-enabled {
            type boolean;
            default true;
            description
             "Enables user authentication via RADIUS server.";
          }
          leaf fallback-to-local {
            when '../nokia-ext-aaa:auth-enabled = "true"';
            type boolean;
            default true;
            description
              "In case that RADIUS server is not reachable, fallback to local authentication is performed.";
          }
        }
      }
    } //external-authentication
  } // augment
} // module
