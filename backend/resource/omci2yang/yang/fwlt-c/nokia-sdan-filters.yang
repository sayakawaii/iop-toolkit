module nokia-sdan-filters {
  yang-version 1.1;
  namespace "urn:bbf:yang:nokia-sdan-filters";

  prefix nokia-sdan-filt;

  import bbf-dot1q-types {
    prefix bbf-dot1qt;
  }
  import bbf-qos-classifiers {
    prefix bbf-qos-cls;
  }
  import bbf-frame-classification {
    prefix bbf-classif;
  }
  import ietf-packet-fields {
    prefix packet-fields;
  }
  import bbf-qos-policing {
    prefix bbf-qos-plc;
  }

  organization
    "Nokia";

  contact
    "Comments or questions about this Nokia YANG module should be
     directed to <mailto:isam.yang@nokia.com>.";

  description
    "This module contains a collection of YANG definitions for
     supporting Nokia specific requirements as applicable to its
     access network equipment.

     Specifically, this module contains definitions of filter
     criteria.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2023, Nokia. All Rights Reserved.";

  revision 2023-05-18 {
    description
      "Initial revision.";
    reference
      "Nokia specific";
  }

  feature match-on-specific-ipv4-header-fields {
    description
      "This feature indicates whether the system supports classifying
       packets based on the IP header fields that are specific for
       IPv4 packets with the purpose of giving the matching packets a
       special QoS treatment.";
  }

  feature match-on-specific-ipv6-header-fields {
    description
      "This feature indicates whether the system supports classifying
       packets based on the IP header fields that are specific for
       IPv6 packets with the purpose of giving the matching packets a
       special QoS treatment.";
  }

  feature match-on-common-ip-header-fields {
    description
      "This feature indicates whether the system supports classifying
       packets based on the IP header fields that are common for IPV4
       and IPv6 packets with the purpose of giving the matching
       packets a special QoS treatment.";
  }

  grouping acl-transport-header-fields {
    description
      "Transport header fields";
    container source-port-range {
      presence
        "The presence of this container enables configuration of the
         source port range.

         If the container is not present, then the source port is not
         a filter criterion and then, as to this filter, 'all packets
         match'.";
      description
        "Set of alternatives to specify one or more source ports. The
         range case provides an inclusive range of source ports
         through the specification of a lower port and an upper port.
         The operator case allows to specify a single port and an
         operator that together identify a single or a set of ports.
         For example, the use of the operator equal identifies the
         single specified port.";
      uses packet-fields:port-range-or-operator {
        refine "port-range-or-operator" {
          mandatory true;
        }
      }
    }
    container destination-port-range {
      presence
        "The presence of this container enables configuration of the
         destination port range.

         If the container is not present, then the destination port is
         not a filter criterion and then, as to this filter, 'all
         packets match'.";
      description
        "Set of alternatives to specify one or more destination ports.
         The range case provides an inclusive range of destination
         ports through the specification of a lower port and an upper
         port. The operator case allows to specify a single port and
         an operator that together identify a single or a set of
         ports. For example, the use of the operator equal identifies
         the single specified port.";
      uses packet-fields:port-range-or-operator {
        refine "port-range-or-operator" {
          mandatory true;
        }
      }
    }
  }

  grouping extended-filter {
    description
      "List of filters to be used as criteria for classifying
       frames.";
    container source-mac-address {
      presence
        "The presence of this container enables configuration of a
         filter on the source MAC address.

         If the container is not present, then the source MAC address
         is not a filter criterion and then, as to this filter, 'all
         frames match'.";
      leaf filter-match {
        type boolean;
        default "true";
        description
          "This is logical operator for a filter.

           When true, it indicates the filter looks for a match with
           a pattern defined by the filter-field. When false, it looks
           for a 'no match' with the pattern defined by the filter
           field.";
      }
      uses bbf-classif:mac-address-match {
        refine "mac-address" {
          mandatory true;
        }
      }
      description
        "Filter containing source MAC address.";
    }
    container destination-mac-address {
      presence
        "The presence of this container enables configuration of a
         filter on the destination MAC address.

         If the container is not present, then the destination MAC
         address is not a filter criterion and then, as to this
         filter, 'all frames match'.";
      leaf filter-match {
        type boolean;
        default "true";
        description
          "This is logical operator for a filter.

           When true, it indicates the filter looks for a match with
           a pattern defined by the filter-field. When false, it looks
           for a 'no match' with the pattern defined by the filter
           field.";
      }
      uses bbf-classif:mac-address-match {
        refine "mac-address" {
          mandatory true;
        }
      }
      description
        "Filter containing destination MAC address.";
    }
    container vlans {
      presence
        "The presence of this container enables configuration of a
         filter on VLAN tags.

         If the container is not present, then the presence or absence
         of VLAN tags in the frame is not a filter criterion and then,
         as to this filter, 'all frames match'.";
      description
        "Match criteria associated with VLAN tags.";
      choice vlan-match {
        mandatory true;
        description
          "Match based on VLAN tag.";
        case match-untagged {
          leaf untagged {
            type empty;
            description
              "Match all untagged traffic.";
          }
        }
        case match-vlan-tagged {
          list tag {
            key "index";
            min-elements 1;
            max-elements 2;
            description
              "Provides values to evaluate against frame's their
               corresponding VLAN tag fields. When multiple match
               criteria are specified, then all of them must evaluate
               positive to have a match. The outermost tag is
               assigned index 0. ";
            leaf index {
              type bbf-classif:tag-index;
              must 'count(../../tag[index = 0]) > 0' {
                error-message
                  "An inner tag can only be matched on when also "
                + "matching on an outer tag.";
                description
                  "Only allow matching on an inner tag, if also
                   matching on the outer tags at the same time.";
              }
              description
                "The index into the tag stack with the outermost tag
                 represented by index 0.";
            }
            uses bbf-qos-cls:in-pbit-list;
            uses bbf-qos-cls:in-dei;
          }
        }
      }
    }
    leaf-list ethernet-frame-type {
      type bbf-dot1qt:ether-type-or-acronym;
      description
        "The value to be compared with the first Ethertype of an
         untagged Ethernet frame; or for frames that contain one or
         more VLAN tags it is the value to be compared with the
         Ethertype that is defined by the context where this grouping
         is used. It can be even the Ethertype that identifies a VLAN
         tag.

         If the leaf is not configured, then the Ethertype is not a
         filter criterion and then, as to this filter,
         'all frames match'.";
    }
    container ipv4 {
      if-feature
        "match-on-specific-ipv4-header-fields";
      presence
        "The presence of this container enables configuration of a
         filter on fields of the IP header specific to IPv4.
         Configuration within this container enables filtering for the
         corresponding packet field. Packet fields without
         configuration are not subject to filtering.

         If the container is not present, then IPv4 specific header
         fields are not a filter criterion and then, as to this
         filter, 'all packets match'.";
      uses packet-fields:acl-ipv4-header-fields;
      description
        "Rule set that matches IPv4 headers.";
    }
    container ipv6 {
      if-feature
        "match-on-specific-ipv6-header-fields";
      presence
        "The presence of this container enables configuration of a
         filter on fields of the IP header specific to IPv6.
         Configuration within this container enables filtering for the
         corresponding packet field. Packet fields without
         configuration are not subject to filtering.

         If the container is not present, then IPv6 specific header
         fields are not a filter criterion and then, as to this
         filter, 'all packets match'.";
      uses packet-fields:acl-ipv6-header-fields;
      description
        "Rule set that matches IPv6 headers.";
    }
    container ip-common {
      if-feature "match-on-common-ip-header-fields";
      presence
        "The presence of this container enables configuration of a
         filter on fields of the IP header common to both IPv4 and
         IPv6. Configuration within this container enables filtering
         for the corresponding packet field. Packet fields without
         configuration are not subject to filtering.

         If the container is not present, then fields that are common
         for IPv4 and IPv6 headers are not a filter criterion and
         then, as to this filter, 'all packets match'.";
      leaf dscp-range {
        type bbf-classif:dscp-range-or-any;
        description
          "String identifying the DSCP values and/or range.";
      }
      uses packet-fields:acl-ip-header-fields;
      description
        "Rule set that matches for common IPv4 and IPv6 header
         fields.";
    }
    container transport {
      if-feature "match-on-common-ip-header-fields";
      presence
        "The presence of this container enables configuration of a
         filter on source and/or destination port numbers.
         Configuration within this container enables filtering for the
         corresponding packet field. Packet fields without
         configuration are not subject to filtering.

         If the container is not present, then the source and/or
         destination port number in IP headers are not a filter
         criterion and then, as to this filter, 'all packets match'.";
      uses acl-transport-header-fields;
      description
        "Rule set that matches port numbers in IP headers.";
    }
    leaf-list protocol {
      type bbf-classif:protocols;
      description
        "This leaf-list provides a set of protocols as a filter
         criterion for classifying frames with the intention to apply
         actions at matching condition.

         There is a match if the frame is of one of the protocols
         specified in the leaf-list. If the leaf-list is not
         configured, then the protocol is not a filter criterion and
         then, as to this filter, 'all frames match'.";
    }
    list pbit-marking-list {
      key "index";
      description
        "The pbit marking list provides match criteria for classifying
         frames with the intention to apply actions at matching
         condition. The p-bits fields to be evaluated are part of a
         frame's metadata as provided as output of another QoS policy.

         The match criteria provides a list because a frame can
         contain multiple VLAN tags and correspondingly can contain
         multiple metadata p-bits fields.

         There is a match if all the frame's metadata p-bits fields
         have a match with one of the values of the corresponding
         'pbit-value' in this list. If the list is not configured,
         then the metadata p-bits fields are not a filter criterion
         and then, as to this filter, 'all frames match'.";
      leaf index {
        type bbf-qos-cls:qos-pbit-marking-index;
        description
          "The index associated with a metadata value of the p-bits.";
      }
      leaf-list pbit-value {
        type bbf-dot1qt:pbit;
        min-elements 1;
        description
          "This leaf-list provides a set of possible values of the
           p-bits as a criterion for classifying frames.

           There is a match if the identified frame's metadata p-bits
           is one of the values specified in the leaf-list.";
      }
    }
    list dei-marking-list {
      key "index";
      description
        "The DEI marking list provides match criteria for classifying
         frames with the intention to apply actions at matching
         condition. The DEI fields to be evaluated are part of a
         frame's metadata as provided as output of another QoS policy.

         The match criteria provides a list because a frame can
         contain multiple VLAN tags and correspondingly can contain
         multiple metadata DEI fields.

         There is a match if all the frame's metadata DEI fields have
         a match with the corresponding 'dei-values' in this list. If
         the list is not configured, then the metadata DEI fields are
         not a filter criterion and then, as to this filter, 'all
         frames match'.";
      leaf index {
        type bbf-qos-cls:qos-dei-marking-index;
        description
          "The index associated with a metadata DEI value.";
      }
      leaf dei-value {
        type bbf-dot1qt:dei;
        mandatory true;
        description
          "A DEI value as a criterion for classifying frames.";
      }
    }
    leaf-list flow-color {
      type bbf-qos-plc:qos-color;
      description
        "This leaf-list provides a set of flow colors as a filter
         criterion for classifying frames with the intention to apply
         actions at matching condition. The flow color to be evaluated
         can be part of a frame's metadata as provided as output of
         another QoS policy.

         There is a match if the frame has a flow-color that is one
         of the values specified in the leaf-list. If the leaf-list is
         not configured, then the flow-color is not a filter criterion
         and then, as to this filter, 'all frames match'.";
    }
  }
}
