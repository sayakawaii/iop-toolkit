module nokia-bbf-xpongemtcont-mounted-eonu-only-dev {
yang-version 1.1;
  namespace
    "http://www.nokia.com/Fixed-Networks/BBA/yang/nokia-bbf-xpongemtcont-mounted-eonu-only-dev";

  prefix nokia-bbf-xpongemtcont-mounted-eonu-only-dev;

  import bbf-fiber-onu-emulated-mount {
    prefix onu;
  }

  import ietf-interfaces-mounted{
    prefix if-mounted;
  }

  import bbf-sub-interfaces-mounted {
    prefix bbf-subif-mounted;
  }

  import bbf-xpongemtcont-mounted {
    prefix bbf-xpongemtcont-mounted;
  }

  import iana-if-type-mounted {
    prefix ianaift-mounted;
  }

  import bbf-sub-interface-tagging-mounted {
    prefix bbf-subif-tag-mounted;
  }

  import nokia-template-common {
    prefix template-common;
  }

  organization
    "Nokia";

  contact
    "isam.yang@nokia.com";
  
  description
    "This module contains a collection of YANG deviations on top
     of standard for supporting BBF/bbf-xpongemtcont-tcont-body YANG module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";


  revision 2023-06-22 {
    description
      "add deviation yang to check some leaf must be configured";
    reference
      "Nokia specific";
  }

  deviation "/onu:onus/onu:onu/onu:root/bbf-xpongemtcont-mounted:xpongemtcont/bbf-xpongemtcont-mounted:gemports/bbf-xpongemtcont-mounted:gemport" {
    deviate add {
      must "not(derived-from-or-self(../../../../onu:usage, 'template-common:node-actual-usage'))"  
            + " or "
            + "not(derived-from-or-self(deref(current()/bbf-xpongemtcont-mounted:interface)/../if-mounted:type, 'ianaift-mounted:ethernetCsmacd'))"
            + " or "
            + "(count(../bbf-xpongemtcont-mounted:gemport[deref(bbf-xpongemtcont-mounted:interface)/../bbf-subif-mounted:subif-lower-layer/bbf-subif-mounted:interface=current()/bbf-xpongemtcont-mounted:interface])=0)" {
            error-message "gemport cannot reference VSI that subif-lower-layer is gemsharing UNI.";
      }
    }
  }

  deviation "/onu:onus/onu:onu/onu:root/bbf-xpongemtcont-mounted:xpongemtcont/bbf-xpongemtcont-mounted:gemports/bbf-xpongemtcont-mounted:gemport/bbf-xpongemtcont-mounted:interface" {
    deviate add {
      must "not(derived-from-or-self(../../../../../onu:usage, 'template-common:node-actual-usage'))"  
            + " or "
            + "not(derived-from-or-self(deref(current())/../if-mounted:type, 'ianaift-mounted:ethernetCsmacd'))"
            + " or "
            + "(count(current()/../../../../if-mounted:interfaces/if-mounted:interface[bbf-subif-mounted:subif-lower-layer/bbf-subif-mounted:interface = current()]"
            + "/bbf-subif-mounted:inline-frame-processing[bbf-subif-mounted:egress-rewrite/bbf-subif-tag-mounted:pop-tags = 0][not(boolean(bbf-subif-mounted:egress-rewrite/bbf-subif-tag-mounted:push-tag))]"
            + "/bbf-subif-mounted:ingress-rule/bbf-subif-mounted:rule[bbf-subif-mounted:flexible-match/bbf-subif-tag-mounted:match-criteria"
            + "/bbf-subif-tag-mounted:tag/bbf-subif-tag-mounted:dot1q-tag/bbf-subif-tag-mounted:vlan-id = 'priority-tagged']"
            + "[bbf-subif-mounted:ingress-rewrite/bbf-subif-tag-mounted:pop-tags = 0][not(boolean(bbf-subif-mounted:ingress-rewrite/bbf-subif-tag-mounted:push-tag))]) = 0"
            + " and "
            + "count(current()/../../../../if-mounted:interfaces/if-mounted:interface[bbf-subif-mounted:subif-lower-layer/bbf-subif-mounted:interface = current()]"
            + "/bbf-subif-mounted:inline-frame-processing[bbf-subif-mounted:egress-rewrite/bbf-subif-tag-mounted:pop-tags = 0][not(boolean(bbf-subif-mounted:egress-rewrite/bbf-subif-tag-mounted:push-tag))]"
            + "/bbf-subif-mounted:ingress-rule/bbf-subif-mounted:rule[bbf-subif-mounted:ingress-rewrite/bbf-subif-tag-mounted:pop-tags = 0][not(boolean(bbf-subif-mounted:ingress-rewrite/bbf-subif-tag-mounted:push-tag))]"
            + "/bbf-subif-mounted:flexible-match/bbf-subif-tag-mounted:match-criteria/bbf-subif-tag-mounted:untagged) = 0)"
            {

            error-message "cannot configure priority-tag transparent or untag transparent VSIs under the UNI that is referenced by gemsharing gemport.";

      }
    }
  }

  deviation "/onu:onus/onu:onu/onu:root/bbf-xpongemtcont-mounted:xpongemtcont/bbf-xpongemtcont-mounted:gemports/bbf-xpongemtcont-mounted:gemport/bbf-xpongemtcont-mounted:interface" {
    deviate add {
      must "not(derived-from-or-self(../../../../../onu:usage, 'template-common:node-actual-usage'))
             or
            (count(../../bbf-xpongemtcont-mounted:gemport[bbf-xpongemtcont-mounted:interface=current()][bbf-xpongemtcont-mounted:traffic-class=current()/../bbf-xpongemtcont-mounted:traffic-class]) <= 1)" {

          error-message "gemport traffic-class should be unique under same interface.";
      }
    }
  }

}
