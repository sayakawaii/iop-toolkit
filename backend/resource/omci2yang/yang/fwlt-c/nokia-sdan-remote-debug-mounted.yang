module nokia-sdan-remote-debug-mounted {
  yang-version 1.1;

  namespace "urn:bbf:yang:nokia-sdan-remote-debug-mounted";

  prefix nokia-sdan-rmt-dbg-mounted;

  import bbf-fiber-onu-emulated-mount {
    prefix onu;
  }

  import nokia-template-common {
    prefix template-common;
  }

  import bbf-yang-types {
    prefix bbf-yang;
  }

  organization
    "Nokia";

  contact
   "Comments or questions about this Nokia YANG module should be
    directed to <mailto:isam.yang@nokia.com>.";

  description
   "This module contains a collection of YANG definitions for
    supporting Nokia specific requirements as applicable to
    ONU remote debugging.

    Specifically this module contains a collection of Yang
    definitions for debugging an ONU from OLT via
    standard managed entity (ME 158)

    This specification is published by Nokia under Non-Disclosure
    Agreement(s) (NDA) with specific parties and has to be considered
    as Confidential Information as defined in such NDA. Nokia
    reserves the right to revise this document for any reason,
    including but not limited to conformity with standards
    promulgated by various agencies, utilisation of advances in the
    state of the technical areas, or the reflection of changes in the
    design of any equipment, techniques, or procedures described or
    referred to herein.

    The product specifications and other technical or performance
    information contained herein are subject to change without
    notice. Updates of this document will be issued under the above
    NDA's.

    Nokia makes no representation or warranty, expressed or implied,
    with respect to the sufficiency, accuracy, or utility of any
    information or opinion contained herein. Nokia expressly advises
    that any use of for any purpose or reliance upon this technical
    reference is at the risk of the user and that Nokia shall not be
    liable for any damage or injury incurred by any person arising
    out of the sufficiency, accuracy, or utility of any information
    or opinion contained herein.

    This document is not to be construed as a suggestion to any
    manufacturer to modify or change any of its products, nor does
    this document represent any commitment by Nokia to sell or
    purchase any product. Nothing contained herein shall be construed
    as conferring by implication, estoppel, or otherwise any license
    or right under any patent, whether or not the use of any
    information herein necessarily employs an invention of any
    existing or later issued patent.

    Nokia reserves the right not to offer any or all of these
    products and to withdraw any or all of them at any future time.

    Copyright (C) 2022, Nokia. All Rights Reserved.";

   revision 2022-03-04 {
     description
       "Initial revision.";
     reference
       "Nokia specific.";
   }

  identity remote-dbg-cmd-status {
    description
     "The status of execution of an ONU remote debug command.";
  }

  identity no-failure {
    base remote-dbg-cmd-status;
    description
      "The ONU remote debug command was executed successfully and output
       is provided.";
  }

  identity no-failure-truncated-output {
    base remote-dbg-cmd-status;
    description
      "The ONU remote debug command was executed successfully but the
       output exceeded the maximum of 4K bytes that can be reported. A
       truncated report is provided.";
  }

  identity no-response {
    base remote-dbg-cmd-status;
    description
     "The ONU does not respond on a remote debug command.";
  }

  identity command-failure {
    base remote-dbg-cmd-status;
    description
     "The ONU responds with a failure for the executed remote debug
      command.";
  }

  augment '/onu:onus/onu:onu/onu:root' {
    when "derived-from-or-self(../onu:usage, 'template-common:node-actual-usage') or "
       + "derived-from-or-self(../onu:usage, 'template-common:node-from-template-usage')" {
      description
        "It should be a node-actual-usage or node-from-template-usage
         ONU for remote debug configuration.";
    }
    description "augment onu for remote debug";
    container onu-remote-dbg {
      config false;
      description
       "Provides the support for debugging ONU via standard OMCI
        Remote Debug ME 158.";
      leaf onu-supported-cmd-format {
        type enumeration {
          enum ascii-format {
            description
             "The ONU supports the ASCII String format for both
              command and reply.";
          }
          enum free-format {
            description
              "The ONU supports the vendor-specific format.";
          }
          enum unsupported {
            description
              "The ONU does not support the remote debug feature.";
          }
        }
        default "unsupported";
        description
         "Identifies the format of the command and reply that the ONU
          supports.";
      }

      action set-remote-dbg-cmd {
        description
          "Request to send a remote debug command to the ONU.";
        input {
          leaf context-id {
            type bbf-yang:string-ascii64;
            mandatory true;
            description
              "A key to co-relate the input command and the output
               received through notification.";
          }

          choice onu-dbg-cmd {
            mandatory true;
            description
              "ONU debug commands to be sent to ONU.";
            case ascii-format {
              leaf ascii-format {
                type string {
                  length "1..250";
                  pattern '[ -~]*';
                }
                description
                  "To send vendor-specific debug commands to the ONU
                   in ASCII format.";
              }
            }
            case free-format {
              leaf free-format {
                type string {
                  length "1..251";
                  pattern '0x(([A-Fa-f0-9]{2})*)';
                }
                description
                  "To send vendor-specific debug commands to the ONU
                   in free-format(Hex).";
              }
            }
          }
        }
      }
      notification remote-dbg-cmd-result {
        description
          "Provides the result of a Remote debug Command collected
           from ONU via ME 158.";

        leaf context-id {
          type bbf-yang:string-ascii64;
         mandatory true;
          description
            "A key to co-relate this notification to the prior
             'set-remote-dbg-cmd' action.";
        }

        leaf remote-dbg-cmd-status {
          type identityref {
            base remote-dbg-cmd-status;
          }
          description
            "Provides the status of the command sent as a result of
             the 'set-remote-dbg-cmd' action identified through the
             'context-id'.";
        }

        leaf remote-dbg-cmd-output {
          when "../remote-dbg-cmd-status != 'nokia-sdan-rmt-dbg-mounted:no-response' and "
              + "../remote-dbg-cmd-status != 'nokia-sdan-rmt-dbg-mounted:command-failure'" {
            description
              "Only valid when there is an output from the ONU.";
          }
          type string {
            length "1..4096";
          }
          mandatory true;
          description
            "Provides the command output retrieved from the ONU for
             the command sent as a result of the 'set-remote-dbg-cmd'
             action identified through the 'context-id'.";

        }
      }
    }
  }
}
