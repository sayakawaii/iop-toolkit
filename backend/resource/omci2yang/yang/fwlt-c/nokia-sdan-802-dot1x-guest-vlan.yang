module nokia-sdan-802-dot1x-guest-vlan {
  yang-version 1.1;
  namespace "http://www.nokia.com/Fixed-Networks/BBA/yang/"
          + "nokia-sdan-802-dot1x-guest-vlan";
  prefix "nokia-sdan-guest-vlan";

  import ietf-interfaces {
    prefix "if";
  }
  import ieee802-dot1x {
    prefix "dot1x";
  }
  import nokia-802-dot1x-ext {
    prefix "nokia-dot1x-ext";
  }
  import ietf-system {
    prefix "sys";
  }
  import bbf-l2-forwarding {
    prefix bbf-l2-fwd;
  }
  import bbf-interface-usage {
      prefix bbf-if-usg;
  }

  organization
    "Nokia";

  contact
    "Comments or questions about this Nokia YANG module should be
     directed to <mailto:isam.yang@nokia.com>.";

  description
    "This module contains a collection of YANG definitions for
     supporting Nokia specific requirements as applicable to its
     access network equipment.

     Specifically, this module augments the standard IEEE model with
     data for when the system shall initiate authentication.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2026, Nokia. All Rights Reserved.";

  revision 2026-01-16 {
    description
      "Initial revision with new leaf under system pae
       and interface pae to configure and enable guest VLAN feature";
    reference
      "Nokia specific";
  }


  augment "/sys:system/dot1x:pae-system" {
    description
      "Extends the configuration of the PAE at system level.";

    list guest-vlan {
      key "guest-vlan";
      description
        "list of forwarders to be used for guest VLAN";
      leaf guest-vlan {
        type bbf-l2-fwd:forwarder-ref;
        must "not(/if:interfaces/if:interface[/bbf-l2-fwd:forwarding/bbf-l2-fwd:forwarders/bbf-l2-fwd:forwarder[bbf-l2-fwd:name = current()]/"
           + "bbf-l2-fwd:ports/bbf-l2-fwd:port/bbf-l2-fwd:sub-interface]/bbf-if-usg:interface-usage/bbf-if-usg:interface-usage = 'user-port')" {
          error-message "forwarder configured for guest VLAN should not have user-port attached";
        }
        description
          "forwarder to be used for guest VLAN";
      }
    }
  }

  augment "/if:interfaces/if:interface/dot1x:pae/nokia-dot1x-ext:ext-authenticator" {
    description
      "Extends the configuration of the PAE at interface level.";

    container guest-vlan {
      when '(../nokia-dot1x-ext:authentication-mode = "port") or
            (../nokia-dot1x-ext:authentication-mode = "mac-based")' {
          description
            "Applies when authentication-mode is mac-based or mab-based.";
      }
      presence
        "The presence of this container indicates the presence of
        guest VLAN feature in the V-ENET";
      description
        "Contains forwarder to be used under guest VLAN
         for this v-ENET.";

      leaf guest-vlan {
        type nokia-sdan-guest-vlan:sys-guest-vlan-ref;
        description
          "Configure one of the forwarders configured at system level
           to be used for guest VLAN of this v-ENET";
      }
    }
  }

  typedef sys-guest-vlan-ref {
    type leafref {
      path "/sys:system/dot1x:pae-system/nokia-sdan-guest-vlan:guest-vlan/nokia-sdan-guest-vlan:guest-vlan";
    }
    description
      "this used by data model need reference to system list of guest VLAN forwarders";
  }
}
