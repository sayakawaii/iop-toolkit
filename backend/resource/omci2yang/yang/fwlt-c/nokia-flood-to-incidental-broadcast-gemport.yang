module nokia-flood-to-incidental-broadcast-gemport {
  yang-version 1.1;
  namespace "uri:http://www.nokia.com/Fixed-Networks/BBA/yang/"
          + "nokia-flood-to-incidental-broadcast-gemport";
	    
  prefix "nokia-flood-to-incidental-broadcast-gemport";

  import bbf-l2-forwarding {
    prefix bbf-l2-fwd;
  }
  
//  import bbf-l2-forwarding-flooding-policies {
//    prefix bbf-l2fwd-flood-pol;
//  }

  organization
    "Nokia";

  contact
    "Comments or questions about this Nokia YANG module should be 
     directed to <mailto:isam.yang@nokia.com>.";

  description
    "This module contains a collection of YANG definitions for 
     supporting Nokia specific requirements as applicable to its 
     access network equipment.
     
     Specifically, this module augments the forwarding flooding policy 
	 profile with a flag for indicating flood traffic forwarded to 
	 incidental broadcast gemports.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2019, Nokia. All Rights Reserved.";

  revision 2019-12-06 {
    description
      "Initial revision.";
      
    reference
      "BBF TR-301, Architecture and Requirements for Fiber to the 
       Distribution Point";
  }

  augment '/bbf-l2-fwd:forwarding/bbf-l2-fwd:'
         +'flooding-policies-profiles/bbf-l2-fwd:'
         +'flooding-policies-profile' {
    description
      "Augments the forwarding flooding policy profile 
       with a flag of flood-to-incidental-broadcast-gemport.";

    leaf flood-to-incidental-broadcast-gemport {
      type boolean;
      default "false";
      description
        "This flag applies on all downstream flooding traffics of the forwarder 
         which quotes this flooding policies profile.
         If the action of a policy is configured as discard, traffic meet 
         with this policy always discarded, no matter this flag is true or false.
         If flag is true and the action of a policy is configured as forward, 
         the traffic meet with this policy will not be forwarded to individual 
         UNI/NNI VSIs on top of unicast-gem-ports, but a single copy will
         be sent to the incidental-broadcast-gemport.
         If flag is false or the system doesn't sport incidental broadcast 
         gem ports, the system will work in the normal way: flooding to 
         forwarder ports or forwarder groups as configured.";
    }
  }
}
