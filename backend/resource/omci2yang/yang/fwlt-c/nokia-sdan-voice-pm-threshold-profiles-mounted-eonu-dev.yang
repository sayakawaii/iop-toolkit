module nokia-sdan-voice-pm-threshold-profiles-mounted-eonu-dev {
  yang-version 1.1;
  namespace "http://www.nokia.com/Fixed-Networks/BBA/yang/"
  + "nokia-sdan-voice-pm-threshold-profiles-mounted-eonu-dev";
  prefix nokia-voice-pm-tca-prof-mounted-eonu-dev;
  
  import bbf-fiber-onu-emulated-mount {
    prefix onu;
  }

  import nokia-hardware-profiles-mounted {
    prefix nokia-hw-prof-mounted;
  }

  import nokia-sdan-hardware-pm-threshold-profiles-mounted {
    prefix nokia-hw-pm-threshold-prof-mounted;
  }

  import nokia-sdan-voice-pm-threshold-profiles-mounted {
    prefix nokia-voice-pm-threhsold-profiles-mounted;
  }

  organization
    "Nokia";
  contact
    "Nokia";
  description
    "This module contains a collection of YANG deviations on top of NOKIA specific POTS interworking PM TCA profile yang module";

  revision 2023-06-14 {
    description
      "Limits the values of the threshold between 1 and (2^32)-2.";
    reference "Nokia specific";
  }
  
  revision 2023-03-11 {
    description
      "Adding deviations for restricting number of TCA profiles for POTS interworking PM";
    reference "Nokia specific";
  }
  
  deviation "/onu:onus/onu:onu/onu:root/nokia-hw-prof-mounted:tca-profiles/nokia-hw-pm-threshold-prof-mounted:pm-profiles/nokia-voice-pm-threhsold-profiles-mounted:ccpm-failure-profile" {
    deviate add {
      must "count(current()/../nokia-voice-pm-threhsold-profiles-mounted:ccpm-failure-profile) <= 10" {
      error-message "Exceeds maximum number of ccpm-failure-profile supported in the system.";
      description
        "This deviation limits the number of ccpm-failure-profile configured per system to 10.";
      }
    }
  }

  deviation "/onu:onus/onu:onu/onu:root/nokia-hw-prof-mounted:tca-profiles/nokia-hw-pm-threshold-prof-mounted:pm-profiles/nokia-voice-pm-threhsold-profiles-mounted:ccpm-failure-profile/nokia-voice-pm-threhsold-profiles-mounted:call-setup-fail-threshold" {
    description
      "This deviation limits the values of the threshold between 1 and (2^32)-2.";
    deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:ccpm-failure-profile/nokia-voice-pm-threhsold-profiles-mounted:call-setup-timeout-threshold" {
    description
      "This deviation limits the values of the threshold between 1 and (2^32)-2.";
    deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:ccpm-failure-profile/nokia-voice-pm-threhsold-profiles-mounted:call-terminate-threshold" {
    description
      "This deviation limits the values of the threshold between 1 and (2^32)-2.";
    deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:ccpm-failure-profile/nokia-voice-pm-threhsold-profiles-mounted:port-release-no-dialing-threshold" {
    description
      "This deviation limits the values of the threshold between 1 and (2^32)-2.";
    deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:ccpm-failure-profile/nokia-voice-pm-threhsold-profiles-mounted:port-offhook-timeout-threshold" {
    description
      "This deviation limits the values of the threshold between 1 and (2^32)-2.";
    deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:rtp-failure-profile" {
    deviate add {
      must "count(current()/../nokia-voice-pm-threhsold-profiles-mounted:rtp-failure-profile) <= 10" {
      error-message "Exceeds maximum number of rtp-failure-profile supported in the system.";
      description
        "This deviation limits the number of rtp-failure-profile configured per system to 10.";
      }
    }
  }

  deviation "/onu:onus/onu:onu/onu:root/nokia-hw-prof-mounted:tca-profiles/nokia-hw-pm-threshold-prof-mounted:pm-profiles/nokia-voice-pm-threhsold-profiles-mounted:rtp-failure-profile/nokia-voice-pm-threhsold-profiles-mounted:rtp-errors-threshold" {
    description
      "This deviation limits the values of the threshold between 1 and (2^32)-2.";
    deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:rtp-failure-profile/nokia-voice-pm-threhsold-profiles-mounted:rtp-packet-loss-threshold" {
    description
      "This deviation limits the values of the threshold between 1 and (2^32)-2.";
    deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:rtp-failure-profile/nokia-voice-pm-threhsold-profiles-mounted:max-jitter-threshold" {
    description
      "This deviation limits the values of the threshold between 1 and (2^32)-2.";
   deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:rtp-failure-profile/nokia-voice-pm-threhsold-profiles-mounted:max-rtcp-inter-packet-time-threshold" {
    description
      "This deviation limits the values of the threshold between 1 and (2^32)-2.";
    deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:rtp-failure-profile/nokia-voice-pm-threhsold-profiles-mounted:buffer-underflow-threshold" {
    description
      "This deviation limits the values of the threshold between 1 and (2^32)-2.";
    deviate replace {
      type uint32 {
        range "1..4294967294";
      }
    }
  }

  deviation "/onu:onus/onu:onu/onu:root/nokia-hw-prof-mounted:tca-profiles/nokia-hw-pm-threshold-prof-mounted:pm-profiles/nokia-voice-pm-threhsold-profiles-mounted:rtp-failure-profile/nokia-voice-pm-threhsold-profiles-mounted:buffer-overflow-threshold" {
    description
      "This deviation limits the values of the threshold between 1 and (2^32)-2.";
    deviate replace {
      type uint32 {
        range "1..4294967294";
      }
    }
  }
  
}
