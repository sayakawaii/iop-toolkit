module nokia-sdan-rf-video-ani-frommounted {
  yang-version 1.1;
  namespace "http://www.nokia.com/Fixed-Networks/BBA/yang/"
             + "nokia-sdan-rf-video-ani-frommounted";
  prefix nokia-rf-ani-frommounted;
  

  import ietf-interfaces-frommounted {
     prefix if-frommounted;
  }
  
  import bbf-fiber-onu-emulated-mount {
     prefix onu;
  }

  organization
    "Nokia";

  contact
    "Comments or questions about this Broadband Forum YANG module
     should be directed to <mailto:isam.yang@nokia.com>.";


  description
    "This module contains a collection of YANG definitions for
     Physical path termination point video ANI.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";


  revision 2023-04-25 {
    description
      "Initial revision.";
   reference
      "Nokia specific";
  }
  
  typedef agc-mode {
    type enumeration {
      enum "no-agc" {
        description
          "No AGC";
      }
      enum "broad-band-agc" {
        description
          "Broadband RF AGC.";
      }
      enum "optical-agc" {
        description
          "Optical AGC.";
      }
    }
    description "type agc-mode";
  }
  
  
  augment "/onu:onus/onu:onu/onu:fromroot/if-frommounted:interfaces/if-frommounted:interface" {
    description
      "Augments config nodes for RF video ANI.";

    container rf-video-ani {
      presence "rf-video-ani";
      description
        "The config node of RF video ANI.";
      reference
        "ITU-T G.988 9.13.2 Physical path termination point video ANI.";
      
      leaf agc-mode {
        type agc-mode;
        description
          "This attribute allows the configuration of
           the ONU's AGC mode.";
        reference
          "ITU-T G.988 9.13.2 Physical path termination point
           video ANI: AGC mode.";
      }
      
      leaf agc-offset {
        type int8 {range "-120 .. 120";}
        description
          "This attribute indicates the measurement offset that 
            the ONU should use in AGC. The attribute has a step 
            size of 0.1 dB, represented as a signed integer.
            
           The theoretical nominal RF signal is 80 channels of
            NTSC video, each with a per-channel OMI of 3.5%. 
            An ONU presented with such a signal should produce 
            its specified output when this attribute is set to zero.
            
           If total optical power is used for AGC, this attribute 
            provides the OMI offset for any NTSC carriers present 
            from the theoretical 3.5% value. For example, if the 
            actual signal uses an OMI of 7.0% per channel (3 dB higher), 
            then the ONU should be given an AGC setting of 30 (coded 0x1E).
            
           If broadband RF power is used for AGC, this attribute 
            provides the total power offset for any NTSC carriers 
            present from the theoretical 80-channel value. For example,
            if an actual signal contains 40 NTSC channels (3 dB lower), 
            then the ONU should be given an AGC setting of -30 (coded 0xE2).";
        reference
          "ITU-T G.988 9.13.2 Physical path termination point
           video ANI: AGC setting.";
      }
      
      leaf lower-optical-threshold {
        type int8 {range "-120 .. 60";}
        description
          "This attribute specifies the optical level used to declare
           the video OOR low alarm. Valid values are -12 to +6 dBm in 0.1 
           dB increments, represented as a 2s complement integer. 
           (Coding -120 to +60, where 0x00 = 0 dBm, 0x88 = -12.0 dBm, etc.) 
           Upon ME instantiation, the ONU sets this attribute to 
           0xA1 (-9.5 dBm).";
        reference
          "ITU-T G.988 9.13.2 Physical path termination point
           video ANI: Video lower optical threshold.";
      }
      
      leaf upper-optical-threshold {
        type int8 {range "-120 .. 60";}
        description
          "This attribute specifies the optical level used to declare
           the video OOR high alarm. Valid values are -12 to +6 dBm in 0.1 dB 
           increments, represented as a 2s complement integer. 
           (Coding -120 to +60, 0x00 = 0 dBm, 0x88 = -12.0 dBm, etc.) 
           Upon ME instantiation, the ONU sets this attribute to 
           0x19 (+2.5 dBm).";
        reference
          "ITU-T G.988 9.13.2 Physical path termination point
           video ANI: Video upper optical threshold.";
      }
    }
  }
  
}
