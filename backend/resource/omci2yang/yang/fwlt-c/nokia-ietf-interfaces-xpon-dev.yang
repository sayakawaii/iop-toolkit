module nokia-ietf-interfaces-xpon-dev {

  namespace "http://www.nokia.com/Fixed-Networks/BBA/yang/"
    + "nokia-ietf-interfaces-xpon-dev";

  prefix nokia-ietf-interfaces-xpon-dev;

  import ietf-interfaces {
    prefix if;
  }

  import bbf-xpon-if-type {
    prefix bbf-xponift;
  }

  organization
    "Nokia";

  contact
    "isam.yang@nokia.com";

  description
    "The NOKIA IETF/System YANG module supporting
     deviations on top of standard.";

  revision 2024-08-26 {
    description
      "Correct the error message";
    reference
      "Nokia Specific.";
  }

  revision 2023-02-24 {
    description
      "enabled must be true for olt-v-enet.";
    reference
      "Nokia Specific.";
  }

  revision 2022-12-10 {
    description
      "Initial revision.";
    reference
      "Nokia Specific.";
  }


  deviation "/if:interfaces/if:interface/if:link-up-down-trap-enable" {
    deviate add {
        must "(current()/../if:type != 'bbf-xponift:channel-group') and
              (current()/../if:type != 'bbf-xponift:channel-partition') and
              (current()/../if:type != 'bbf-xponift:channel-pair') and
              (current()/../if:type != 'bbf-xponift:channel-termination') and
              (current()/../if:type != 'bbf-xponift:v-ani') and
              (current()/../if:type != 'bbf-xponift:olt-v-enet')"
      {
        error-message "The link-up-down-trap-enable not supported on this interface.";
      }
    }
  }

  deviation "/if:interfaces/if:interface/if:enabled" {
    deviate add {
      must "current() = 'true' or current()/../if:type != 'bbf-xponift:olt-v-enet'" {
        error-message "The enabled must be true for olt-v-enet.";
      }
    }
  }
}
