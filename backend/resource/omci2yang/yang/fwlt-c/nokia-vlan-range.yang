module nokia-vlan-range {
  yang-version 1.1;
  namespace "http://www.nokia.com/Fixed-Networks/BBA/yang/"
          + "nokia-vlan-range";

  prefix nokia-vlan-range;

  import bbf-yang-types {
    prefix bbf-yang;
  }

  import bbf-dot1q-types{
    prefix bbf-dot1qt;
  }

  organization
    "Nokia";

  contact
    "Comments or questions about this Nokia YANG module should be 
     directed to <mailto:isam.yang@nokia.com>.";

  description
    "This module contains a collection of YANG definitions for 
     supporting Nokia specific requirements as applicable to its 
     access network equipment.
     
     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2019, Nokia. All Rights Reserved.";

  revision 2019-11-22 {
    description
      "Initial revision.
       * Approval Date:    see revision date above.
       * Publication Date: yyyy-mm-dd.";
    reference
      "Nokia specific";
  }
  
  container vlan-range-profiles {  
    description
      "protocol range configuration profiles.";

    list vlan-range-profile {
      key "name";
      description
        "List containing the parameters for the protocol range 
         configuration.";

      leaf name {
        type bbf-yang:string-ascii64;
        description
          "Name of the profile.";
      }

      leaf range {
        type bbf-dot1qt:vlan-id-range;
        mandatory true;
        description
          "The leaf specifies the set of VLAN-ids for which protocol
           awareness is applied. The frame's VLAN tag against which 
           the device shall evaluate this range is:
           - the first VLAN-tag after the VLAN-tags (if any) that 
           were used to classify ingress frames into a 
           VLAN sub-interface,
           - the first VLAN-tag after the VLAN-tags (if any) that 
           remain after the egress frame processing for egress frame 
           on this VLAN sub-interface.";
      }
    }
  }

  typedef vlan-range-profile-name {
    type leafref {
      path "/nokia-vlan-range:vlan-range-profiles" +
           "/nokia-vlan-range:vlan-range-profile" +
           "/nokia-vlan-range:name";	 
    }
    description
      "A reference to protocol range profile.";
  }
}
