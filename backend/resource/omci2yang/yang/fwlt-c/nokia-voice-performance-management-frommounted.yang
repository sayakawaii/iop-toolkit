module nokia-voice-performance-management-frommounted {
  yang-version 1.1;
  namespace "http://www.nokia.com/Fixed-Networks/BBA/yang/"
    + "nokia-voice-performance-management-frommounted";
  prefix  nokia-voice-pm-frommounted;

  import bbf-sip-voip-frommounted  {
    prefix bbf-sip-voip-frommounted;
  }
  import bbf-fiber-onu-emulated-mount {
     prefix onu;
  }
  organization
    "Nokia";
  contact
    "Comments or questions about this Nokia YANG module should be
     directed to <mailto:isam.yang@nokia.com>.";
  description
    "This module contains a collection of YANG definitions for
     supporting Nokia specific requirements as applicable to its
     access network equipment.
     Specifically, this module augments the bbf-xponcommon-performance-management
     model with additional Nokia specific PM counters.
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.
     The product specifications and other technical or performance
     information contained herein are subject to change without
     notice. Updates of this document will be issued under the above
     NDA's.
     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
     Nokia reserves the right not to offer any or all of these
     products and to withdraw any or all of them at any future time.
     Copyright (C) 2022, Nokia. All Rights Reserved.";

  revision 2025-06-04 {
    description
      "Added support for PM counter group profile for the VOIP interfaces";
    reference
      "Nokia specific for EPIC BBN-107831";
  }

  revision 2022-12-22 {
    description
      "Support for voice performance monitoring TCA profiles configurtaion and TCA notification.";
    reference
      "Nokia specific";
  }

  revision 2022-02-16 {
    description
      "Initial revision";
    reference
      "Nokia specific";
  }

  grouping performance-monitoring-config {
      description
          "Configuration support to enable performance monitoring.";
      container performance {
        presence "performance";
          description
              "Performance parameters.";

          leaf enable {
              type boolean;
              description
                  "Enables performance counters on this SIP User Agent and media forwarder.";
          }
      }
  }

  augment '/onu:onus/onu:onu/onu:fromroot/bbf-sip-voip-frommounted:pots-interworking-nodes/bbf-sip-voip-frommounted:pots-interworking' {
      description
          "Data nodes for the performance configuration parameters.";

      uses nokia-voice-pm-frommounted:performance-monitoring-config;
  }


  augment "/onu:onus/onu:onu/onu:fromroot/bbf-sip-voip-frommounted:pots-interworking-nodes/bbf-sip-voip-frommounted:pots-interworking"
         + "/nokia-voice-pm-frommounted:performance" {
      description
        "Data nodes for threshold crossing alert configuration parameters";

      leaf tca-pots-call-control-profile {
           type string;
         description
            "Reference to the voice call control performance monitoring TCA profile. TCA is disabled when no profile is referenced";
      }
      leaf tca-pots-rtp-profile {
          type string;
          description
            "Reference to the voice call control performance monitoring TCA profile. TCA is disabled when no profile is referenced";
      }
      leaf-list pots-pm-group {
	  type pots-iw-pm-group-type;
	  description
	    "Performance monitoring group type to enable or disable
	     specific POTS UNI performance monitoring counters";
      }
  }

  typedef pots-iw-pm-group-type {
      type enumeration {
          enum "call-control-pm" {
              description
                 "This enables the performance monitoring of POTS interworking node counters.
                 When this PM counter group type is enabled, the below POTS performance counters
                 are enabled:
                     call-attempt-failures, call-terminate-failures, maximum-call-setup-duration,
                     maximum-off-hook-duration, releases-without-dialing
                 These counters are enabled for intervals-15min current and history
                 performance data";
          }
          enum "rtp-pm" {
              description
                 "This enables the performance monitoring of RTP packet counters.
                 When this PM counter group type is enabled, the below media performance counters
                 for RTP are enabled:
                     out-rtp-packets, in-rtp-packets rtp-packet-errors, rtp-packet-loss,
                     maximum-time-rtcp-packets, maximum-jitter, buffer-underflows, buffer-overflows
                 These counters are enabled for intervals-15min current and history
                 performance data";
          }
      }
      description "type definition";
}
}
