module nokia-ietf-netconf-acm-li-nacm-dev {
  yang-version "1.1";
  namespace "http://www.nokia.com/Fixed-Networks/BBA/yang/nokia-ietf-netconf-acm-li-nacm-dev";
  prefix nokia-ietf-netconf-acm-li-nacm-dev;

  import ietf-netconf-acm {
    prefix "nacm";
  }

  organization "Nokia";

  contact
    "Comments or questions about this Nokia YANG module should be
     directed to <mailto:isam.yang@nokia.com>.";

  description
    "The NOKIA li-nacm/nokia-ietf-netconf-acm-li-nacm-dev YANG module
     supports li specific deviations on top of ietf-netconf-acm
     standard.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2025, Nokia. All Rights Reserved.";

  revision 2025-12-25 {
    description
      "Initial version LS26.3.
      Limit maximum Li users in system to 1.
      Users in any other group cannot be part of li-user-config-access-group
      and vice versa";
    reference
      "Nokia specific";
  }

  deviation "/nacm:nacm/nacm:groups/nacm:group/nacm:user-name" {
    deviate add {
      must "../nacm:name != 'li-user-config-access-group' or
      count(/nacm:nacm/nacm:groups/nacm:group/user-name[. = current()] ) = 1" {
        error-message
          "User-names in group 'li-user-config-access-group' cannot be configured"
          +" in any other group, and user-name in any other group cannot be"
          +" configured in 'li-user-config-access-group'.";
      }
    }
  }

  deviation "/nacm:nacm/nacm:groups" {
    deviate add {
      must "(count(group[name='li-user-config-access-group']/user-name)<=1)"{
        error-message "Only 1 user is allowed for li-user-config-access-group.";
        description "Only 1 user is allowed for li-user-config-access-group.";
      }
    }
  }
}
