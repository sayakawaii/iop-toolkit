module nokia-sdan-mib-upload-behavior-types-frommounted {
  yang-version 1.1;

  namespace "http://www.nokia.com/Fixed-Networks/BBA/yang/"
           + "nokia-sdan-mib-upload-behavior-types-frommounted";

  prefix nokia-sdan-mib-upload-behavior-types-frommounted;

  organization
    "Nokia";

  contact
    "Comments or questions about this Nokia YANG module should be
     directed to <mailto:isam.mibsupport@nokia.com>.";

  description
    "This module contains a collection of YANG definitions for
     supporting Nokia specific requirements as applicable to its
     access network equipment.

     Specifically, this module contains a collection of YANG
     definitions for adapting the ONU MIB upload behavior.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2024-12-12 {
    description
      "Initial revision.
       Augmenting onu-management with a parameter to define the
       desired mib upload behavior
       * Approval Date:    see revision date above.
       * Publication Date: 2024-10-04.";
    reference
      "Nokia specific";
  }

  identity mib-upload-mode {
    description
      "Defines the MIB upload behavior towards an ONU.";
  }

  identity mib-upload-per-onu-flavor {
    base mib-upload-mode;
    description
      "Only perform MIB upload when the first ONU of a particular flavor
      (vendor-id/hw-version/sw-version) is discovered, to reduce system load
      and improved performance. For subsequent discovery of ONUs of the same
      flavor, the MIB upload is not performed and the MIB upload data of the
      first ONU of this flavor that was discovered is reused.";
  }

  identity mib-upload-per-onu {
    base mib-upload-mode;
    description
      "Always perform MIB upload when an ONU is MIB-reset or discovered,
      unless the ONU has already the desired configuration (MDS is equal at
      ONU and OLT side and different from zero).";
  }

}
