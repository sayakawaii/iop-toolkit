module nokia-sdan-li-system {
  yang-version 1.1;
  namespace "http://www.nokia.com/Fixed-Networks/BBA/yang/"
          + "nokia-sdan-li-system";
  prefix nokia-li-sys;

  import ietf-interfaces {
    prefix if;
  }

  import bbf-if-type {
    prefix bbfift;
  }

  import bbf-interface-usage {
    prefix bbf-if-usg;
  }

  organization
     "Nokia";
  contact
    "Comments or questions about this Nokia YANG module should be
     directed to <mailto:isam.yang@nokia.com>.";

  description
    "This module contains a collection of YANG definitions for
     supporting the requirements to allow lawful interception
     system level configurations.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2025, Nokia. All Rights Reserved.";

  revision 2026-01-28 {
    description
      "Description content changes to lawful intercept";
    reference
       "Nokia specific";
  }

  revision 2026-01-12 {
    description
      "Description content change to li";
    reference
       "Nokia specific";
  }

  revision 2026-01-06 {
    description
      "Container name change to li";
    reference
      "Nokia specific";
  }

  revision 2025-01-03 {
    description
      "Initial Revision";
    reference
      "Nokia specific";
  }

  container li-system {
    presence
      "Presence of this container indicates Lawful Intercept
         functionality is supported on this system.";
    description
      "System level configurations for lawful interception.";
    leaf li-vlan-sub-interface {
      type if:interface-ref;
      must "((derived-from-or-self(/if:interfaces/if:interface"
          +"[if:name = current()]/if:type,"
          +"'bbfift:vlan-sub-interface'))"
          +"and(/if:interfaces/if:interface[if:name = current()]/"
          +"bbf-if-usg:interface-usage/bbf-if-usg:interface-usage "
          +"= 'network-port'))" {

        error-message
          "'li-vlan-sub-interface' can only refer to an interface which is a vlan-sub-interface (or its derived type) and which is configured as a network-port.";

        description
          "This leaf can only refer to an interface if it is
           configured with an if:type as vlan-sub-interface or its
           derived type and
           bbf-if-usg:interface-usage/bbf-if-usg:interface-usage as
           network-port";
      }
      description
        "The VLAN sub-interface which will be used to send the
         intercepted packet out of the system.";
    }
  }
}
