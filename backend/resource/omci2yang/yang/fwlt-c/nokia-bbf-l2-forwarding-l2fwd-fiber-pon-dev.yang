module nokia-bbf-l2-forwarding-l2fwd-fiber-pon-dev {

  namespace "http://www.nokia.com/Fixed-Networks/BBA/yang/" +
            "nokia-bbf-l2-forwarding-l2fwd-fiber-pon-dev";

  prefix nokia-bbf-l2-forwarding-l2fwd-fiber-pon-dev;

  import bbf-l2-forwarding {
    prefix bbf-l2-fwd;
  }

  import ietf-interfaces {
    prefix if;
  }

  import bbf-if-type {
    prefix bbfift;
  }
  
  organization
    "Nokia";

  contact
    "isam.yang@nokia.com";

  description
    "This module contains a collection of YANG deviations on top
     of standard for supporting relative YANG module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2024-04-30 {
    description
      "remove the support of mac-learning-failure-action";
    reference
      "Nokia specific";
  }

  revision 2022-11-24 {
    description
      "Remove unsupported yang node.";
    reference
      "Nokia specific";
  }
  
  revision 2022-01-26 {
    description
      "Initial revision.";
    reference
      "Nokia specific";
  }

  deviation "/bbf-l2-fwd:forwarding/bbf-l2-fwd:forwarders/bbf-l2-fwd:forwarder/bbf-l2-fwd:flooding-policies/bbf-l2-fwd:flooding-policy-type/bbf-l2-fwd:forwarder-specific"
  {
    deviate not-supported;
  }

  /*deviation "/if:interfaces/if:interface/bbf-l2-fwd:mac-learning/bbf-l2-fwd:number-committed-mac-addresses"
  {
    deviate not-supported;
  }*/
  
  /*Sum of static MAC in VSI must be less than or equal to max-mac per VSI.*/
  deviation "/bbf-l2-fwd:forwarding/bbf-l2-fwd:forwarding-databases/bbf-l2-fwd:forwarding-database/bbf-l2-fwd:static-mac-address"
          +"/bbf-l2-fwd:learning-constraint/bbf-l2-fwd:install-in-fdb-on/bbf-l2-fwd:install-on/bbf-l2-fwd:static-port"
          +"/bbf-l2-fwd:static-forwarder-port-ref/bbf-l2-fwd:port" {
    deviate add{
      must "count(/bbf-l2-fwd:forwarding/bbf-l2-fwd:forwarding-databases/bbf-l2-fwd:forwarding-database"
           +"/bbf-l2-fwd:static-mac-address[bbf-l2-fwd:static-forwarder-port-ref/bbf-l2-fwd:port = current()])"
           +"<= /if:interfaces/if:interface[if:type = 'bbfift:vlan-sub-interface' and"
           +" if:name = /bbf-l2-fwd:forwarding/bbf-l2-fwd:forwarders"
           +"/bbf-l2-fwd:forwarder/bbf-l2-fwd:ports/bbf-l2-fwd:port[bbf-l2-fwd:name=current()]/bbf-l2-fwd:sub-interface]"
           +"/bbf-l2-fwd:mac-learning/max-number-mac-addresses"
      {
        error-message "Sum of Static MACs per vlan-sub-interface exceeds max-number-mac-addresses of the vlan-sub-interface";
      }
    }
  }

  deviation "/if:interfaces/if:interface/bbf-l2-fwd:mac-learning"
            +"/bbf-l2-fwd:mac-learning-failure-action" {
    description "In pon mode, the interface does't support mac-learning";
    deviate not-supported;
  }
}
