module nokia-xponinfra-cac {
  yang-version 1.1;
  namespace "http://www.nokia.com/Fixed-Networks/BBA/yang/"
          + "nokia-xponinfra-cac";

  prefix nokia-xponinfra-cac;

  import ietf-interfaces {
    prefix if;
  }

  import bbf-xpon {
    prefix bbf-xpon;
  }

  organization
    "Nokia";

  contact
    "Comments or questions about this Nokia YANG module should be
     directed to <mailto:isam.yang@nokia.com>.";

  description
    "This module contains a collection of YANG definitions for
     supporting Nokia specific requirements as applicable to its
     access network equipment.

     Specifically, this module contains definitions of filter
     criteria.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2017, Nokia. All Rights Reserved.";


  revision 2021-09-16 {
    description
      "Add the upstream and downstream Layer2 Ethernet capacity.";
    reference
      "Nokia specific";
  }

  revision 2020-04-08 {
    description
      "Initial revision";
    reference
      "Nokia specific";
  }

  typedef l2-capacity-megabit {
    type decimal64 {
      fraction-digits 3;
      range "0..max";
    }
    units "megabit/second";
    description
      "A type which represents the interface Layer2 capacity.";
  }

  augment "/if:interfaces-state/if:interface/bbf-xpon:channel-pair" {
    description
      "The bandwidth of the channel pair.";

    leaf avail-us-unicast-bw {
      type l2-capacity-megabit;
      description
        "This represents the currently remaining Layer 2 Ethernet 
         upstream bandwidth that is available for unicast 
         services on top of those already provisioned. 
         Layer 2 Ethernet data is to be understood as the 
         part of the Ethernet frame from the Destination MAC 
         address, included, up to the Frame Check Sequence (FCS),
         included. Ethernet frame details can be found for instance
         in IEEE Std 802.3-2018, IEEE Standard for Ethernet, 
         Section 1, Chapter 3 'Media Access Control (MAC) frame 
         and packet Specifications'.
         Note that because of the xPON transport overhead structure, 
         this capacity depends on the number of active ONUs, on the 
         number of configured Services (T-CONTs) on ONUs and on
         whether Forward Error Correction (FEC) is used or not. 
         Also a conventional traffic pattern with an average 
         frame size of 361 bytes is considered when coping 
         with xPON framing overhead."; 
   }

    leaf us-l2-capacity {
      type l2-capacity-megabit;
      description
        "This represents the upstream capacity of the channel 
         pair to transport Layer2 Ethernet data. 
         Layer 2 Ethernet data is to be understood as the 
         part of the Ethernet frame from the Destination MAC 
         address, included, up to the Frame Check Sequence (FCS),
         included. Ethernet frame details can be found for instance
         in IEEE Std 802.3-2018, IEEE Standard for Ethernet, 
         Section 1, Chapter 3 'Media Access Control (MAC) frame 
         and packet Specifications'.
         Note that because of the xPON transport overhead structure, 
         this capacity depends on the number of active ONUs, on the 
         number of configured Services (T-CONTs) on ONUs and on 
         whether Forward Error Correction (FEC) is used or not. 
         Also a conventional traffic pattern with an average 
         frame size of 361 bytes is considered when coping 
         with xPON framing overhead."; 
    }

    leaf ds-l2-capacity {
      type l2-capacity-megabit;
      description
        "This represents the downstream capacity of the channel 
         pair to transport Layer2 Ethernet data. 
         Layer 2 Ethernet data is to be understood as the 
         part of the Ethernet frame from the Destination MAC 
         address, included, up to the Frame Check Sequence (FCS),
         included. Ethernet frame details can be found for instance
         in IEEE Std 802.3-2018, IEEE Standard for Ethernet, 
         Section 1, Chapter 3 'Media Access Control (MAC) frame 
         and packet Specifications'. 
         Note that this capacity depends on whether Forward Error 
         Correction (FEC) is used or not.
         Also a conventional traffic pattern with an average 
         frame size of 361 bytes is considered when coping 
         with xPON framing overhead."; 
    }
  }

  augment "/if:interfaces-state/if:interface/bbf-xpon:channel-pair" {
    description
      "The notification when available upstream bandwidth changed.";

    notification avail-us-unicast-bw-changed {
      description
        "A notification when available bandwidth changed.";
      leaf avail-us-unicast-bw {
        type l2-capacity-megabit;
        mandatory true;
        description
          "This represents the currently remaining Layer 2 Ethernet 
           upstream bandwidth that is available for unicast 
           services on top of those already provisioned. 
           Layer 2 Ethernet data is to be understood as the 
           part of the Ethernet frame from the Destination MAC 
           address, included, up to the Frame Check Sequence (FCS),
           included. Ethernet frame details can be found for instance
           in IEEE Std 802.3-2018, IEEE Standard for Ethernet, 
           Section 1, Chapter 3 'Media Access Control (MAC) frame 
           and packet Specifications'.
           Note that because of the xPON transport overhead structure, 
           this capacity depends on the number of active ONUs, on the 
           number of configured Services (T-CONTs) on ONUs and on
           whether Forward Error Correction (FEC) is used or not. 
           Also a conventional traffic pattern with an average 
           frame size of 361 bytes is considered when coping 
           with xPON framing overhead."; 
      }
    }

    notification l2-capacity-changed {
      description
        "A notification when the Layer2 Ethernet capacity changed.";
      leaf us-l2-capacity {
        type l2-capacity-megabit;
        mandatory true;
        description
          "This represents the upstream capacity of the channel 
           pair to transport Layer2 Ethernet data. 
           Layer 2 Ethernet data is to be understood as the 
           part of the Ethernet frame from the Destination MAC 
           address, included, up to the Frame Check Sequence (FCS),
           included. Ethernet frame details can be found for instance
           in IEEE Std 802.3-2018, IEEE Standard for Ethernet, 
           Section 1, Chapter 3 'Media Access Control (MAC) frame 
           and packet Specifications'.
           Note that because of the xPON transport overhead structure, 
           this capacity depends on the number of active ONUs, on the 
           number of configured Services (T-CONTs) on ONUs and on 
           whether Forward Error Correction (FEC) is used or not. 
           Also a conventional traffic pattern with an average 
           frame size of 361 bytes is considered when coping 
           with xPON framing overhead."; 
      }

      leaf ds-l2-capacity {
        type l2-capacity-megabit;
        mandatory true;
        description
          "This represents the downstream capacity of the channel 
           pair to transport Layer2 Ethernet data. 
           Layer 2 Ethernet data is to be understood as the 
           part of the Ethernet frame from the Destination MAC 
           address, included, up to the Frame Check Sequence (FCS),
           included. Ethernet frame details can be found for instance
           in IEEE Std 802.3-2018, IEEE Standard for Ethernet, 
           Section 1, Chapter 3 'Media Access Control (MAC) frame 
           and packet Specifications'. 
           Note that this capacity depends on whether Forward Error 
           Correction (FEC) is used or not.
           Also a conventional traffic pattern with an average 
           frame size of 361 bytes is considered when coping 
           with xPON framing overhead."; 
      }
    }
  }

}
