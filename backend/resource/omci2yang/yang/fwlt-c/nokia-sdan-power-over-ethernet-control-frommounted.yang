module nokia-sdan-power-over-ethernet-control-frommounted {
  yang-version 1.1;
  namespace "http://www.nokia.com/Fixed-Networks/BBA/yang/"
             + "nokia-sdan-power-over-ethernet-control-frommounted";
  prefix nokia-poe-ctr-frommounted;

  

  import ietf-hardware-frommounted {
    prefix hw-frommounted;
  }

  import bbf-fiber-onu-emulated-mount {
    prefix onu;
  }

  
  organization
    "Nokia";

  contact
    "Comments or questions about this Broadband Forum YANG module
     should be directed to <mailto:isam.yang@nokia.com>.";

  description
    "This module contains a collection of YANG definitions for
     Power over Ethernet control(POE).

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2025-04-15 {
    description
      "extend the type range of yang leaf pse-class-control";
    reference
      "Epic BBN-207669";
  }

  revision 2024-09-11 {
    description
      "remove operational data related when statement";
    reference
      "BBN-107706";
  }

  revision 2022-01-18 {
    description
      "Initial revision.";
   reference
      "Nokia specific";
  }
  
  augment "/onu:onus/onu:onu/onu:fromroot/hw-frommounted:hardware/hw-frommounted:component" {
    description 
      "Augment model for configurations for 
       power over ethernet.";
    container poe {
      presence "poe";
      description
        "Controls the PoE capability of a power-sourcing 
         equipment (PSE).";
      reference 
        "ITU-T G.988 9.5.6 Power over Ethernet control.";
      leaf enable {
        type boolean;
        description
          "This leaf controls whether power is provided to external 
           equipment over this Ethernet UNI.";
        reference 
          "ITU-T G.988 9.5.1 Physical path termination point 
           Ethernet UNI: Power control.";
      }
      leaf pse-class-control {
        type uint16 {
            range "0..9";
        }
        description
          "Used to place specific limits on the class of power 
           supported by this port. Optional leaf.
           0: Power Feed Enabled at default level.
           1: Power Feed Enabled at Class 0 power level.
           2: Power Feed Enabled at Class 1 power level.
           3: Power Feed Enabled at Class 2 power level.
           4: Power Feed Enabled at Class 3 power level.
           5: Power Feed Enabled at Class 4 power level.
           6: Power Feed Enabled at Class 5 power level.
           7: Power Feed Enabled at Class 6 power level.
           8: Power Feed Enabled at Class 7 power level.
           9: Power Feed Enabled at Class 8 power level. ";
        reference 
          "ITU-T G.988 9.5.6 Power over Ethernet control: 
           PsE class control.";
      }
      leaf power-priority {
        type enumeration {
          enum "critical" {
            description
              "Indicates that the most highst power priority.";
          }
          enum "high" {
            description
              "Indicates that the high power priority.";
          }
          enum "low" {
            description
              "Indicates that the low power priority.";
          }
        }
        description
          "This leaf controls the priority of the port from the point
           of view of a power management algorithm. The priority that
           is set by this leaf could be used by a control mechanism 
           that prevents overcurrent situations by first disconnecting
           ports with lower power priority (higher numerical value).
           Optional leaf.";
        reference 
          "ITU-T G.988 9.5.6 Power over Ethernet control: Power priority.";
      }
    }
  }

}
