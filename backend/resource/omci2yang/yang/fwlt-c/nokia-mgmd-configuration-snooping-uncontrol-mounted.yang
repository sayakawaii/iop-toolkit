module nokia-mgmd-configuration-snooping-uncontrol-mounted {
  yang-version 1.1;
  namespace "http://www.nokia.com/Fixed-Networks/BBA/yang/"
    + "nokia-mgmd-configuration-snooping-uncontrol-mounted";
  prefix  nokia-mc-uncontrol-mounted;  

  import bbf-mgmd-mounted {
    prefix bbf-mgmd-mounted;
  }
  
  import bbf-xpon-if-type-mounted {
      prefix bbf-xponift-mounted;
  }
  
  import ietf-interfaces-mounted {
    prefix if-mounted;
  }
  
  import iana-if-type-mounted {
    prefix ianaift-mounted;
  }
  
  import bbf-fiber-onu-emulated-mount {
     prefix onu;
  }

  organization
    "Nokia";

  contact
    "Comments or questions about this Nokia YANG module should be 
     directed to <mailto:isam.yang@nokia.com>.";

  description
    "This module contains a collection of YANG definitions for 
     supporting Nokia specific requirements as applicable to its 
     access network equipment.
     
     Specifically, this module augments the interface model with data
     specific for the classification and processing of Layer 2 Control
     Protocol (L2CP) frames.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017, Nokia. All Rights Reserved.";

  revision 2021-06-01 {
    description
      "Initial revision.";
    reference
      "TBD";
  }

  identity snoop-transparent-uncontrolled  {
        base bbf-mgmd-mounted:mgmd-mode;
          
          description
            "This identity means that the VPN will snoop upstream IGMP
             or MLD messages and unconditionally send a copy of a MC
             stream to ethernet interface that requests it 
             independently of the VSI carrying the request (i.e. 
             independently of the VLAN-id with which the IGMP or MLD 
             message is received,without check on host permissions and
             without check on the requested multicast channel).

             In this mode, only following objects of VPN are 
             supported:'mode',list of 'ethernet-interface-to-host-
             uncontol'. In particular VPNs in this mode do not make
             use of other YANG leaves.";        
  }

  augment '/onu:onus/onu:onu/onu:root/bbf-mgmd-mounted:multicast/bbf-mgmd-mounted:mgmd/bbf-mgmd-mounted:multicast-vpn'
  {
    description
      "Define the parameters for multicast snooping without control.";  

      list ethernet-interface-to-host-uncontrol {
          when '../bbf-mgmd-mounted:mode = "nokia-mc-uncontrol-mounted:snoop-transparent-uncontrolled"';
          key "interface";          
          description
           "Configuration ethernet interfaces to hosts from which join
            request are accepted without control,independently of the
            VSI carrying them. ";
          
          leaf interface {
            type leafref { path '../../../../../if-mounted:interfaces/if-mounted:interface/if-mounted:name'; }
            must "derived-from-or-self(../../../../../if-mounted:interfaces/if-mounted:interface"
                  +"[if-mounted:name = current()]/if-mounted:type,"
                  +"'bbf-xponift-mounted:onu-v-vrefpoint') or "
                  +"derived-from-or-self(../../../../../if-mounted:interfaces/if-mounted:interface"
                  +"[if-mounted:name = current()]/if-mounted:type,"
                  +"'ianaift-mounted:ethernetCsmacd')" {
              error-message
                "The referenced interface must be 'onu-v-vrefpoint' "
                 + "or 'ethernetCsmacd'.";          
              description
                "The interface must be of the type as 'onu-v-vrefpoint
                 ' or 'ethernetCsmacd'.";
            }
            
            description
              "The interface connects a host. All join requests on the               
               vlan-subinterfaces that exist on top of the interface 
               are accepted unconditionally.";                  
          }
       }
    }
  }
