module nokia-ieee802-dot1q-cfm-no-ccm-dev {

  yang-version 1.1;

  namespace
    "http://www.nokia.com/Fixed-Networks/BBA/yang/"
    + "nokia-ieee802-dot1q-cfm-no-ccm-dev";

  prefix nokia-ieee802-dot1q-cfm-no-ccm-dev;

  import ieee802-dot1q-cfm {
    prefix dot1q-cfm;
  }

  organization
    "Nokia";

  contact
    "Comments or questions about this Nokia YANG module should be
     directed to <mailto:isam.yang@nokia.com>.";

  description
    "This module contains a collection of YANG definitions for
     supporting Nokia specific requirements as applicable to its
     access network equipment.

     Specifically, this module identifies data that potentially
     contains private data. Note that this classification is product
     independent while the support of this data is product dependent.
     I.e. it might be that data that is identified as private is not
     supported in a particular product variant.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2023, Nokia. All Rights Reserved.";

  revision 2023-08-01 {
    description
      "CFM - CCM deviations";
    reference
      "Nokia specific";
  }

  deviation "/dot1q-cfm:cfm/dot1q-cfm:maintenance-domain/"
           +"dot1q-cfm:fault-alarm-transmission" {
    description
      "MD fault-alarm-transmission is not supported.";
    deviate not-supported;
  }

  deviation "/dot1q-cfm:cfm/dot1q-cfm:maintenance-domain/"
           +"dot1q-cfm:maintenance-association/"
           +"dot1q-cfm:fault-alarm-transmission" {
    description
      "MA fault-alarm-transmission is not supported.";
    deviate not-supported;
  }

  deviation "/dot1q-cfm:cfm/dot1q-cfm:maintenance-domain/"
          + "dot1q-cfm:maintenance-association/"
          + "dot1q-cfm:ccm-interval" {
    description
      "ccm-interval is not supported.";
    deviate not-supported;
  }

  deviation "/dot1q-cfm:cfm/dot1q-cfm:maintenance-group/dot1q-cfm:"
          + "mep/dot1q-cfm:inactive-remote-mep" {
    description
      "CCM inactive-remote-mep is not supported.";
    deviate not-supported;
  }

  deviation "/dot1q-cfm:cfm/dot1q-cfm:maintenance-group/dot1q-cfm:"
          + "mep/dot1q-cfm:mep-db" {
    description
      "CCM mep-db is not supported.";
    deviate not-supported;
  }

  deviation "/dot1q-cfm:cfm/dot1q-cfm:maintenance-group/dot1q-cfm:"
          + "mep/dot1q-cfm:continuity-check" {
    description
      "CCM continuity-check is not supported.";
    deviate not-supported;
  }

  deviation "/dot1q-cfm:cfm/dot1q-cfm:maintenance-group/dot1q-cfm:"
          + "mep/dot1q-cfm:stats/dot1q-cfm:mep-ccm-sequence-errors" {
    description
      "CCM mep-ccm-sequence-errors is not supported.";
    deviate not-supported;
  }

  deviation "/dot1q-cfm:cfm/dot1q-cfm:maintenance-group/dot1q-cfm:"
          + "mep/dot1q-cfm:stats/dot1q-cfm:mep-ccms-sent" {
    description
      "CCM mep-ccms-sent is not supported.";
    deviate not-supported;
  }

}
