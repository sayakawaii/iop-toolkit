module nokia-sdan-rf-video-uni-mounted {
  yang-version 1.1;
  namespace "http://www.nokia.com/Fixed-Networks/BBA/yang/"
             + "nokia-sdan-rf-video-uni-mounted";
  prefix nokia-rf-uni-mounted;
  
  import nokia-interface-identities-mounted {
    prefix nokia-if-id-mounted;
  }

  import ietf-interfaces-mounted {
     prefix if-mounted;
  }
  
  import bbf-fiber-onu-emulated-mount {
     prefix onu;
  }


  organization
    "Nokia";

  contact
    "Comments or questions about this Broadband Forum YANG module
     should be directed to <mailto:isam.yang@nokia.com>.";


  description
    "This module contains a collection of YANG definitions for
     Physical path termination point video UNI.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";


  revision 2023-04-25 {
    description
      "Initial revision.";
   reference
      "Nokia specific";
  }
  augment "/onu:onus/onu:onu/onu:root/if-mounted:interfaces/if-mounted:interface" {
    when "derived-from-or-self(if-mounted:type, 
          'nokia-if-id-mounted:rf-video-uni')";
    description
      "Augments config nodes for RF video UNI.";

    container rf-video-uni {
      description
        "The config node of RF video UNI.";
      leaf service-timer {
        type union {
          type enumeration {
            enum undefined {
              description
                "undefined means 'do not care',
                 and NO OMCI messaging is involved.";
            }
          }
          type uint16 {range "0 .. 48";}
        }
        units "hour";
        default undefined;
        description
          "Specifies the amount of time (in hours) the ONT 
           should sustain RF video service while unranged. ";
        reference
          "3HH-11114-FFAA-PBZZA ISAM6_5 OMCI Interface Specification 
           3.1.127 RF Video UNI Supplemental 1.";
      }
      leaf power-control {
        type boolean;
        default "false";
        description
          "This leaf controls whether power is provided to external
           equipment over the video PPTP.";
        reference
          "ITU-T G.988 9.13.1 Physical path termination point video UNI: 
           Power control.";
      }
    }
  }

}
