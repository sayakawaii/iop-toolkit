module ietf-tcp-client {
     yang-version 1.1;
     namespace "urn:ietf:params:xml:ns:yang:ietf-tcp-client";
     prefix tcpc;

     import ietf-inet-types {
       prefix inet;
       reference
         "RFC 6991: Common YANG Data Types";
     }

     import ietf-tcp-common {
       prefix tcpcmn;
       reference
         "RFC XXXX: YANG Groupings for TCP Clients and TCP Servers";
     }

     organization
       "IETF NETCONF (Network Configuration) Working Group and the
        IETF TCP Maintenance and Minor Extensions (TCPM) Working Group";

     contact
       "WG Web:   <http://datatracker.ietf.org/wg/netconf/>
                  <http://datatracker.ietf.org/wg/tcpm/>
        WG List:  <mailto:netconf@ietf.org>
                  <mailto:tcpm@ietf.org>
        Authors:  Kent Watsen <mailto:kent+ietf@watsen.net>
                  Michael Scharf
                  <mailto:michael.scharf@hs-esslingen.de>";

     description
       "This module defines reusable groupings for TCP clients that
        can be used as a basis for specific TCP client instances.

        Copyright (c) 2019 IETF Trust and the persons identified
        as authors of the code. All rights reserved.

        Redistribution and use in source and binary forms, with
        or without modification, is permitted pursuant to, and
        subject to the license terms contained in, the Simplified
        BSD License set forth in Section 4.c of the IETF Trust's
        Legal Provisions Relating to IETF Documents
        (https://trustee.ietf.org/license-info).

        This version of this YANG module is part of RFC XXXX
        (https://www.rfc-editor.org/info/rfcXXXX); see the RFC
        itself for full legal notices.

        The key words 'MUST', 'MUST NOT', 'REQUIRED', 'SHALL',
        'SHALL NOT', 'SHOULD', 'SHOULD NOT', 'RECOMMENDED',
        'NOT RECOMMENDED', 'MAY', and 'OPTIONAL' in this document
        are to be interpreted as described in BCP 14 (RFC 2119)
        (RFC 8174) when, and only when, they appear in all
        capitals, as shown here.";

     revision 2020-03-08 {
       description
         "Initial version";
       reference
         "RFC XXXX: YANG Groupings for TCP Clients and TCP Servers";
     }

     // Features

     feature local-binding-supported {
       description
         "Indicates that the server supports configuring local
          bindings (i.e., the local address and local port) for
          TCP clients.";
     }

     feature tcp-client-keepalives {
       description
         "Per socket TCP keepalive parameters are configurable for
          TCP clients on the server implementing this feature.";
     }

     // Groupings

     grouping tcp-client-grouping {
       description
         "A reusable grouping for configuring a TCP client.

         Note that this grouping uses fairly typical descendent
          node names such that a stack of 'uses' statements will
          have name conflicts.  It is intended that the consuming
          data model will resolve the issue (e.g., by wrapping
          the 'uses' statement in a container called
          'tcp-client-parameters').  This model purposely does
          not do this itself so as to provide maximum flexibility
          to consuming models.";

       leaf remote-address {
         type inet:host;
         mandatory true;
         description
           "The IP address or hostname of the remote peer to
            establish a connection with.  If a domain name is
            configured, then the DNS resolution should happen on
            each connection attempt.  If the DNS resolution
            results in multiple IP addresses, the IP addresses
            are tried according to local preference order until
            a connection has been established or until all IP
            addresses have failed.";
       }
       leaf remote-port {
         type inet:port-number;
         default "0";
         description
           "The IP port number for the remote peer to establish a
            connection with.  An invalid default value (0) is used
            (instead of 'mandatory true') so that as application
            level data model may 'refine' it with an application
            specific default port number value.";
       }
       leaf local-address {
         if-feature "local-binding-supported";
         type inet:ip-address;
         description
           "The local IP address/interface (VRF?) to bind to for when
            connecting to the remote peer.  INADDR_ANY ('0.0.0.0') or
            INADDR6_ANY ('0:0:0:0:0:0:0:0' a.k.a. '::') MAY be used to
            explicitly indicate the implicit default, that the server
            can bind to any IPv4 or IPv6 addresses, respectively.";
       }
       leaf local-port {
         if-feature "local-binding-supported";
         type inet:port-number;
         default "0";
         description
           "The local IP port number to bind to for when connecting
            to the remote peer.  The port number '0', which is the
            default value, indicates that any available local port
            number may be used.";
       }
       uses tcpcmn:tcp-connection-grouping {
         augment "keepalives" {
           if-feature "tcp-client-keepalives";
           description
             "Add an if-feature statement so that implementations
              can choose to support TCP client keepalives.";
         }
       }
     }
   }
