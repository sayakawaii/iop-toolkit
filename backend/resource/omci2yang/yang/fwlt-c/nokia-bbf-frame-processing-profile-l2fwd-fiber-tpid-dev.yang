module nokia-bbf-frame-processing-profile-l2fwd-fiber-tpid-dev {

  namespace "http://www.nokia.com/Fixed-Networks/BBA/yang/" +
            "nokia-bbf-frame-processing-profile-l2fwd-fiber-tpid-dev";

  prefix nokia-bbf-frame-processing-profile-l2fwd-fiber-tpid-dev;

  import bbf-dot1q-types {
    prefix bbf-dot1qt;
  }

  import bbf-frame-processing-profile {
	  prefix bbf-frameproc;
  }

  organization
    "Nokia";

  contact
    "isam.yang@nokia.com";

  description
    "This module contains a collection of YANG deviations on top 
     of standard for supporting BBF/bbf-frame-processing-profile YANG module.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017-2018, Nokia. All Rights Reserved.";

  revision 2020-06-04 {
    description
      "Initial revision.";
    reference
      "Nokia specific"; 
  }

 
  
  /*tag type must be c-vlan*/  
  deviation "/bbf-frameproc:frame-processing-profiles/bbf-frameproc:frame-processing-profile/bbf-frameproc:match-criteria/bbf-frameproc:vlan-tag-match-type/bbf-frameproc:vlan-tagged/bbf-frameproc:tag" {
    deviate add{
	    must "current()/tag-type = 'bbf-dot1qt:c-vlan'"{
		    error-message "The match-criteria tag type must be c-vlan";
	    }
	  }
  }

  deviation "/bbf-frameproc:frame-processing-profiles/bbf-frameproc:frame-processing-profile/bbf-frameproc:egress-rewrite/bbf-frameproc:push-tag" {
    deviate add{
	    must "current()/tag-type = 'bbf-dot1qt:c-vlan' or current()/tag-type = 'tag-type-from-match'"{
		    error-message "The egress-rewrite tag type must be c-vlan or tag-type-from-match";
	    }
	  }
  }
}
