module nokia-dot1x-alarm-types {
  yang-version 1.1;
  namespace "https://www.nokia.com/Fixed-Networks/BBA/yang/nokia-dot1x-alarm-types";
  prefix dot1x-al;
  import nokia-base-alarm-types {
    prefix base-al;
  }
  organization
    "Nokia";
  contact
    "Comments or questions about this Nokia YANG module should be
     directed to <mailto:isam.yang@nokia.com>.";
  description
    "This module provides the details of supported Radius
		 Authenticator alarm types.
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.
     The product specifications and other technical or performance
     information contained herein are subject to change without
     notice. Updates of this document will be issued under the above
     NDA's.
     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
     Nokia reserves the right not to offer any or all of these
     products and to withdraw any or all of them at any future time.
     Copyright (C) 2022, Nokia. All Rights Reserved.";

  revision 2024-07-17 {
    description
      "dynamic-vsi-associated-with-another-sessioon
         - New alarm identity for dot1x-AAA module";
    reference
      "Nokia specific";
  }

  revision 2022-03-15 {
    description
      "dot1x alarm
         - Supported alarm for dot1x module";
    reference
      "Nokia specific";
  }
  identity dot1x-alarm-type {
    base base-al:quality-of-service-alarm;
    description
      "dot1x specific alarm type definitions";
  }
  identity dot1x-alarm {
    base dot1x-alarm-type;
    description
      "abstract alarm type for dot1x application";
  }
  identity dynamic-authorization-attributes-not-present {
    base dot1x-alarm;
    description
      "In the received access-accept request, dynamic authorization
       attributes is expected to be present but not present";
  }
  identity no-dynamic-forwarder-attached-to-vsi {
    base dot1x-alarm;
    description
      "In the received access-accept request, dynamic authorization
       attributes is expected to be present but not present";
  }
  identity no-dynamic-qos-profile-attached-to-vsi {
    base dot1x-alarm;
    description
      "No dynamic qos profile attached to VSI.";
  }
  identity dynamic-vsi-associated-with-another-session {
    base dot1x-alarm;
    description
      "In the received access-accept, VSI name is not expected
       to be part of other existing session";
 }
  identity dot1x-mac-conflict{
    base dot1x-alarm;
    description
      "Detected same mac authenticated on another port, raise mac conflict alarm";
  }

}
