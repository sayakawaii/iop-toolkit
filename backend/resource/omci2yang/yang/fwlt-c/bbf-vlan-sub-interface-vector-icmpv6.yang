module bbf-vlan-sub-interface-vector-icmpv6 {
  yang-version 1.1;
  namespace "urn:bbf:yang:bbf-vlan-sub-interface-vector-icmpv6";
  prefix bbf-vsi-vctr-icmpv6;

  import bbf-vlan-sub-interface-vector {
    prefix bbf-vsi-vctr;
  }

  import bbf-icmpv6 {
    prefix bbf-icmpv6;  
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";
  description
    "This module contains a collection of YANG definitions for
     supporting the Broadband Forum requirements on the management of
     sub-interfaces as applicable to access network equipment. As
     such, this module is specific to access network equipment (e.g.,
     BBF-specified Access Nodes and FTTdp DPUs).

     Specifically, this module extends the VLAN sub-interface vector 
     profile concept with PPPoE data nodes.

     Copyright (c) 2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a4; see
     the TR itself for full legal notices.";

  revision 2021-08-20 {
    description
      "Initial revision.
       * Approval Date:    see revision date above.
       * Publication Date: 20xx-xx-xx.";
    reference
      "TR-383: Common YANG Modules
               <https://www.broadband-forum.org/technical/download/
                        TR-383.pdf>";
  }

  augment "/bbf-vsi-vctr:vsi-vector-profiles"
        + "/bbf-vsi-vctr:vsi-vector-profile" {
    description
      "Augments the vector profile with PPPoE data nodes.";

    container icmpv6 {
      presence
        "Presence of this container indicates icmpv6 relay 
         functionality is supported on this interface.";
      description
        "This container indicates ICMPv6 functionality is 
         supported on this interface.";
      
      leaf icmpv6-filter {
        if-feature bbf-icmpv6:icmpv6-filter;
        type boolean;
        default "false";
        description
          "Manages icmpv6 message forward or discard .
           When it is true, the following messages must be discarded:
           - Downstream Router Solicitation
           - Upstream Router Advertisement 
           - Upstream Redirect
           - Upstream MLD Multicast Listener Queries.
           Forward error and informational messages transparently.
           when it is false, forward messages transparently.";
        reference
          "TR-177 section 5.6.2";
      }

      leaf line-identification-option {
        if-feature bbf-icmpv6:line-identification-option;
        type boolean;
        default "false";
        description
          "Manages the icmpv6 line identification option (LIO)
           insertion/removal in the Router Solicitation
           and Router Advertisement messages.

           When it is true, then before forwarding the packets 
           received on the line the device inserts the LIO data
           based on the syntax configured via icmpv6-profile or
           subscriber-profile, and also adds an IPv6 tunnel header.
           In the reverse direction the devices removes the LIO 
           data before sending the packet on the line.
           When it is false, LIO data does not modify Router 
           Solicitation and Router Advertisement messages.";
           
        reference
          "TR-177 R-15,16";
      }

      leaf profile-ref {
        if-feature bbf-icmpv6:line-identification-option;
        when "../line-identification-option = 'true'" {
          description
            "Applicable only when LIO-insert functionality 
             is enabled.";
        }
        type leafref {
          path '/bbf-icmpv6:icmpv6-profiles/bbf-icmpv6:'
             + 'icmpv6-profile/bbf-icmpv6:name';
        }
        mandatory true;
        description
          "Reference to the icmpv6 configuration profile.";
      }
    }     
  }
}
