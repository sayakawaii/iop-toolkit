module nokia-ietf-interfaces-inexpressible-constraints-validator-l2fwd-fiber-pon-dev {

  yang-version "1.1";
  namespace "http://www.nokia.com/Fixed-Networks/BBA/yang/"
            + "nokia-ietf-interfaces-inexpressible-constraints-validator-l2fwd-fiber-pon-dev";

  prefix nokia-ietf-interfaces-inexpressible-constraints-validator-l2fwd-fiber-pon-dev;

  import ietf-interfaces {
    prefix if;
  }
  
  organization
    "NOKIA";

  contact
    "Comments or questions about this Nokia YANG module should be
     directed to <mailto:isam.yang@nokia.com>.";

  description
    "The NOKIA common/nokia-ietf-interfaces-inexpressible-constraints-validator-l2fwd-fiber-pon-dev
     YANG module supporting deviations on top of ietf-ssh-server standard.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2019, Nokia. All Rights Reserved.";

  revision 2017-04-24 {
    description
      "Initial revision.";
    reference
      "Nokia specific"; 
  }

  deviation "/if:interfaces/if:interface" {
    description
      "Other dependent xpaths where this rule applies are:
        '/bbf-mgmd:multicast/bbf-mgmd:mgmd/bbf-mgmd:multicast-vpn/bbf-mgmd:multicast-interface-to-host'
       The error message 'multicast host interface exceeds maximum user vlan-sub-interface per lower layer in the system.' will be displayed when the constraint is violated.";
    deviate add {}
  }
  
  deviation "/if:interfaces/if:interface" {
    description
      "Other dependent xpaths where this rule applies are:
        '/if:interfaces/nokia-ipv4-sppr:ipv4-security-statistics'
        '/if:interfaces/nokia-ipv6-sppr:ipv6-security-statistics'
       The error message 'Number of vlan-sub-interfaces with statistics (all-available, ipv4-security-stats and ipv6-security-stats) exceeds supported hardware resources.' will be displayed when the constraint is violated.";
    deviate add {}
  }
  
  deviation "/if:interfaces/if:interface" {
    description
      "Reference to the vlan-sub-interface for 802.1x packets, and the interface being referenced must be a 'vlan-sub-interface' and link the same interface.
       The error message 'illegal reference 'pae ext-authenticator signalling-channel' :' will be displayed when the constraint is violated.";
    deviate add {}
  }
  
  deviation "/if:interfaces/if:interface" {
    description
      "Before enable ipv4-security-statistics,prevent-ipv4-address-spoofing should be enabled on the vlan-sub-interface
       Other dependent xpaths where this rule applies are:
        '/if:interfaces/nokia-ipv4-sppr:ipv4-security-statistics'
       The error message 'Before enable ipv4-security-statistics,prevent-ipv4-address-spoofing should be enabled on the vlan-sub-interface' will be displayed when the constraint is violated.";
    deviate add {}
  }
  
  deviation "/if:interfaces/if:interface" {
    description
      "Before enable ipv6-security-statistics,prevent-ipv6-address-spoofing should be enabled on the vlan-sub-interface
       Other dependent xpaths where this rule applies are:
        '/if:interfaces/nokia-ipv6-sppr:ipv6-security-statistics'
       The error message 'Before enable ipv6-security-statistics,prevent-ipv6-address-spoofing should be enabled on the vlan-sub-interface' will be displayed when the constraint is violated.";
    deviate add {}
  }
  
  deviation "/if:interfaces/if:interface" {
    description
      "Other dependent xpaths where this rule applies are:
        '/bbf-frameproc:frame-processing-profiles/bbf-frameproc:frame-processing-profile'
       The error message 'Illegal dual tags on user-port vsi.' will be displayed when the constraint is violated.";
    deviate add {}
  }
  
  deviation "/if:interfaces/if:interface" {
    description
      "The error message 'Network VSI is not allowed to be admin-down status.' will be displayed when the constraint is violated.";
    deviate add {}
  }
  
  deviation "/if:interfaces/if:interface" {
    description
      "Maximum number of vlan-sub-interfaces pbit counter or flow statistics counter supported in the node is exceeded.
       Other dependent xpaths where this rule applies are:
        '/bbf-qos-pol:qos-policy-profiles/bbf-qos-pol:policy-profile'
        '/bbf-qos-pol:policies/bbf-qos-pol:policy'
        '/bbf-qos-cls:classifiers/bbf-qos-cls:classifier-entry'
        '/hw:hardware/hw:component'
       The error message 'Maximum number of vlan-sub-interfaces with pbit counter or flow statistics counter supported in the node is exceeded maximum allowed 1024.' will be displayed when the constraint is violated.";
    deviate add {}
  }
  
  deviation "/if:interfaces/if:interface" {
    description
      "'remoteInterfaceDown' configuration is only supported on a olt-v-enet interface.
       The error message ''remoteInterfaceDown' configuration is only supported on a olt-v-enet interface.' will be displayed when the constraint is violated.";
    deviate add {}
  }
  
}
