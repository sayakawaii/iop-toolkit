module nokia-sdan-hardware-pm-threshold-profiles-mounted-eonu-dev {
  yang-version 1.1;
  namespace "http://www.nokia.com/Fixed-Networks/BBA/yang/"
          + "nokia-sdan-hardware-pm-threshold-profiles-mounted-eonu-dev";
  prefix nokia-hw-pm-threshold-prof-mounted-eonu-dev;

  import bbf-fiber-onu-emulated-mount {
    prefix onu;
  }

  import nokia-hardware-profiles-mounted {
    prefix nokia-hw-prof-mounted;
  }

  import nokia-sdan-hardware-pm-threshold-profiles-mounted {
    prefix nokia-hw-pm-threshold-prof-mounted;
  }

  organization
    "Nokia";
  contact
    "Nokia";
  description
    "This module contains a collection of YANG deviations on top of NOKIA specific CPU PM TCA profile yang module";

  revision 2022-10-13 {
    description
      "Adding deviations for restricting unsupported throsholding values configuration";
    reference "Nokia specific";
  }

  deviation "/onu:onus/onu:onu/onu:root/nokia-hw-prof-mounted:tca-profiles/nokia-hw-pm-threshold-prof-mounted:pm-profiles/nokia-hw-pm-threshold-prof-mounted:system-load-profile" {
    deviate add {
      must "count(current()/../nokia-hw-pm-threshold-prof-mounted:system-load-profile) <= 10" {
      error-message "Exceeds maximum number of system-load-profile supported in the system.";
      description
        "This deviation limits the number of system-load-profile configured per system to 10.";
      }
    }
  }

  deviation "/onu:onus/onu:onu/onu:root/nokia-hw-prof-mounted:tca-profiles/nokia-hw-pm-threshold-prof-mounted:pm-profiles/nokia-hw-pm-threshold-prof-mounted:memory-usage-profile" {
    deviate add {
      must "count(current()/../nokia-hw-pm-threshold-prof-mounted:memory-usage-profile) <= 10" {
      error-message "Exceeds maximum number of memory-usage-profile supported in the system.";
      description
        "This deviation limits the number of memory-usage-profile configured per system to 10.";
      }
    }
  }
}
