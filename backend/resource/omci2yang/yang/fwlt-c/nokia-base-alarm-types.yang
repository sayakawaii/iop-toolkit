module nokia-base-alarm-types {
     yang-version 1.1;
     namespace "https://www.nokia.com/Fixed-Networks/BBA/yang/nokia-base-alarm-types";
     prefix base-al;

     import ietf-alarms {
       prefix al;
     }
     organization
      "Nokia";

     contact
      "Comments or questions about this Nokia YANG module should be
       directed to <mailto:isam.yang@nokia.com>.";

     description
       "This module provides the details of supported base alarm types.

        This specification is published by Nokia under Non-Disclosure
        Agreement(s) (NDA) with specific parties and has to be considered
        as Confidential Information as defined in such NDA. Nokia
        reserves the right to revise this document for any reason,
        including but not limited to conformity with standards
        promulgated by various agencies, utilisation of advances in the
        state of the technical areas, or the reflection of changes in the
        design of any equipment, techniques, or procedures described or
        referred to herein.

        The product specifications and other technical or performance
        information contained herein are subject to change without
        notice. Updates of this document will be issued under the above
        NDA's.

        Nokia makes no representation or warranty, expressed or implied,
        with respect to the sufficiency, accuracy, or utility of any
        information or opinion contained herein. Nokia expressly advises
        that any use of for any purpose or reliance upon this technical
        reference is at the risk of the user and that Nokia shall not be
        liable for any damage or injury incurred by any person arising
        out of the sufficiency, accuracy, or utility of any information
        or opinion contained herein.

        This document is not to be construed as a suggestion to any
        manufacturer to modify or change any of its products, nor does
        this document represent any commitment by Nokia to sell or
        purchase any product. Nothing contained herein shall be construed
        as conferring by implication, estoppel, or otherwise any license
        or right under any patent, whether or not the use of any
        information herein necessarily employs an invention of any
        existing or later issued patent.

        Nokia reserves the right not to offer any or all of these
        products and to withdraw any or all of them at any future time.

        Copyright (C) 2018, Nokia. All Rights Reserved.";

    revision 2023-03-30 {
       description "Add Organization substatement in the module.";        
       reference "Nokia specific.";
    }

    revision 2022-01-13 {
       description
         "Rebase basic alarm types onto ietf-alarms module";
       reference
         "Nokia specific";
     }

     revision 2021-07-27 {
       description
         "Import bbf-alarm-management with standard prefix";
       reference
         "Nokia specific";
     }

     revision 2021-02-04 {
       description
         "Rename yang name with nokia prefix.
           - nokia-base-alarm-types
         ";
       reference
         "Nokia specific";
     }

     revision 2019-07-01 {
      description
        "updates in submodule fast-alarm-types";
      reference
        "Nokia specific";
     }

     revision 2018-02-08 {
      description
        "Base alarms - added rpfBase alarmtype";
       reference
         "Nokia specific";
      }

    identity nokia-alarms {
       base al:alarm-type-id;
       description
         "Nokia specific alarm type definitions";
     }

     identity communications-alarm
     {
       base nokia-alarms;
       description
         "Abstract alarm type for communication alarms";
     }

     identity quality-of-service-alarm {
       base nokia-alarms;
       description
         "Abstract alarm type for QoS alarms";
     }

     identity processing-error-alarm {
       base nokia-alarms;
       description
         "Abstract alarm type for processing-error alarms";
     }

     identity equipment-alarm {
       base nokia-alarms;
       description
         "Abstract alarm type for equipment alarms";
     }

     identity environmental-alarm {
       base nokia-alarms;
       description
         "Abstract alarm type for environmental alarms";
     }

     identity rpf-base-alarm {
       base nokia-alarms;
       description
         "Abstract alarm type for rpf alarms";
     }

    identity onu-alarm {
       base nokia-alarms;
       description
         "Abstract alarm type for Onu alarms";
    }
}
