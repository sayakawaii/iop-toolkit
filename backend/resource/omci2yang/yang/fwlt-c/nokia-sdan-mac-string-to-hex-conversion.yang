module nokia-sdan-mac-string-to-hex-conversion {
  yang-version 1.1;
  namespace "http://www.nokia.com/Fixed-Networks/BBA/yang/"
          + "nokia-sdan-mac-string-to-hex-conversion";
  prefix nokia-sdan-mac-to-hex;

  import ietf-system {
    prefix sys;
  }

  import bbf-subscriber-profiles{
    prefix bbf-subprof;
  }

  organization
    "Nokia";

  contact
    "Comments or questions about this Nokia YANG module should be
     directed to <mailto:isam.yang@nokia.com>.";

  description
    "This module contains a collection of YANG definitions for
     supporting Nokia specific requirements as applicable to its
     access network equipment.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2023, Nokia. All Rights Reserved.";

  revision 2023-11-16 {
    description
      "Description update";
    reference
      "Nokia specific";
  }

  revision 2023-07-31 {
    description
      "Initial revision.
       * Approval Date:    see revision date above.
       * Publication Date: yyyy-mm-dd.";
    reference
      "Nokia specific";
  }

  augment "/sys:system/bbf-subprof:subscriber-management" {
    description "augment subscriber management with mac address conversion";
    leaf mac-address-string-to-hex-conversion {
      type boolean;
      default "false";
      description
        "Enable/Disable the conversion of the MAC address string value
         inserted into PPPoE/DHCPv4/DHCPv6 packets to hexadecimal format.
         When enabled, the string value configured in the circuit-id and
         remote-id YANG parameters of the subscriber profile will be checked
         if they correspond to a case insensitive MAC address using delimiters
         ':', '-' or no delimiters.
         For example 'D4:63:FE:FB:55:01', 'd4-63-fe-fb-55-01' and 'D463fefb5501'
         would all be converted to hex D463FEFB5501.

         Note that a string formatted as 0x123456789abc will always be converted
         into the corresponding MAC address in hex encoded format. This leaf
         configuration value does not change this behavior.";
    }
  }
}
