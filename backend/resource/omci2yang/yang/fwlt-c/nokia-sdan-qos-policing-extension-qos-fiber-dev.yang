module nokia-sdan-qos-policing-extension-qos-fiber-dev {

  namespace
    "http://www.nokia.com/Fixed-Networks/BBA/yang/nokia-sdan-qos-policing-extension-qos-fiber-dev";

  prefix nokia-sdan-qos-policing-extension-qos-fiber-dev;

  import nokia-sdan-qos-policing-extension {
    prefix nokia-qos-plc-ext;
  }

  organization
    "Nokia";

  contact
    "isam.yang@nokia.com";

  description
    "This module contains a collection of YANG deviations on top
     of standard for supporting NOKIA/nokia-sdan-qos-policing-extension
     YANG module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2017-2018, Nokia. All Rights Reserved.";

    /* revision */
  revision 2025-04-15 {
    description
      "Revert policing-pre-handling-profiles/action-profiles dimension limitation.";
    reference
      "Nokia specific";
  }

  /* revision */
  revision 2022-12-29 {
    description
      "Initial revision.";
    reference
      "Nokia specific";
  }

  /* BBN-114329 D-N10 */
  deviation "/nokia-qos-plc-ext:policing-action-profiles/nokia-qos-plc-ext:action-profile"
  {
    deviate add{
      max-elements 512;
    }
  }

  /* BBN-114329 D-N11 */
  deviation "/nokia-qos-plc-ext:policing-pre-handling-profiles/nokia-qos-plc-ext:pre-handling-profile"
  {
    deviate add{
      max-elements 512;
    }
  }


  deviation "/nokia-qos-plc-ext:policing-action-profiles/nokia-qos-plc-ext:action-profile/nokia-qos-plc-ext:action/nokia-qos-plc-ext:action-cfg-params/nokia-qos-plc-ext:assign-metadata/nokia-qos-plc-ext:dei-marking-list"
  {
    /* BBN-114329 D-6 */
    deviate add {
       must "current()/nokia-qos-plc-ext:dei-value = 1"
       {
            error-message "In qos policing action-profile, if the action is DEI-remarking, the remarked DEI value can only be 1.";
       }
    }
  }

  /* BBN-114329 D-8 */
  deviation "/nokia-qos-plc-ext:policing-action-profiles/nokia-qos-plc-ext:action-profile/nokia-qos-plc-ext:action/nokia-qos-plc-ext:action-cfg-params/nokia-qos-plc-ext:assign-metadata/nokia-qos-plc-ext:bac-color"
  {
    deviate add {
       must "current() = ../nokia-qos-plc-ext:flow-color or current() = 'copy-from-flow-color'"
       {
            error-message "For the policing action-profile, when the action is bac-color , the flow-color must be same as it.";
       }
    }
  }

  /* BBN-114329 D-5 */
  deviation "/nokia-qos-plc-ext:policing-pre-handling-profiles/nokia-qos-plc-ext:pre-handling-profile/nokia-qos-plc-ext:pre-handling-entry/nokia-qos-plc-ext:match-params/nokia-qos-plc-ext:dei-marking-list"
  {
    deviate add {
      must "(current()/nokia-qos-plc-ext:dei-value = 0 and ../../nokia-qos-plc-ext:flow-color = 'green')
      or (current()/nokia-qos-plc-ext:dei-value = 1 and ../../nokia-qos-plc-ext:flow-color = 'yellow')"
      {
        error-message "In policing pre-handling profile,if the filter is in-dei/dei-marking-list: when action is green , the dei must be 0; when action is yellow, the dei must be 1; action can not be red";
      }
    }
  }

  /* BBN-114329 D-5 */
  deviation "/nokia-qos-plc-ext:policing-pre-handling-profiles/nokia-qos-plc-ext:pre-handling-profile/nokia-qos-plc-ext:pre-handling-entry/nokia-qos-plc-ext:match-params/nokia-qos-plc-ext:vlans/nokia-qos-plc-ext:tag/nokia-qos-plc-ext:in-dei"
  {
    deviate add {
      must "(current() = 0 and ../../../../nokia-qos-plc-ext:flow-color = 'green')
      or (current() = 1 and ../../../../nokia-qos-plc-ext:flow-color = 'yellow')"
      {
        error-message "In policing pre-handling profile,if the filter is in-dei/dei-marking-list: when action is green , the dei must be 0; when action is yellow, the dei must be 1; action can not be red";
      }
    }
  }
}
