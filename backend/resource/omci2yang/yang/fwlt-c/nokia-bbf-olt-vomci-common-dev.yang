module nokia-bbf-olt-vomci-common-dev {

    namespace
        "http://www.nokia.com/Fixed-Networks/BBA/yang/" +
        "nokia-bbf-olt-vomci-common-dev";

    prefix nokia-bbf-olt-vomci-common-dev;

    import bbf-olt-vomci {
        prefix bbf-olt-vomci;
    }

    import bbf-xponvani {
        prefix bbf-xponvani;
    }

    import ietf-interfaces {
        prefix if;
    }

  organization
    "Nokia";

  contact
    "Comments or questions about this Nokia YANG module should be 
     directed to <mailto:isam.yang@nokia.com>.";

  description
    "This module contains a collection of YANG definitions for 
     supporting Nokia specific requirements as applicable to its 
     access network equipment.
     
     Specifically, this module augments the interface model with data
     specific for the classification and processing of Layer 2 Control
     Protocol (L2CP) frames.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2023, Nokia. All Rights Reserved.";

    revision 2023-03-21 {
        description
        "Initial revision.";
        reference
        "TBD";
    }

    deviation "/bbf-olt-vomci:remote-nf/bbf-olt-vomci:nf-endpoint-filter" {
        description "nf-endpoint-filter list not supported";
        deviate not-supported;
    }

    deviation "/bbf-olt-vomci:remote-nf/bbf-olt-vomci:nf-client/" +
              "bbf-olt-vomci:initiate/bbf-olt-vomci:remote-server/bbf-olt-vomci:on-demand" {
        description "remote-server on-demand must be false";
        deviate add {
            must "current() = 'false'";
        }
    }

    deviation "/bbf-olt-vomci:remote-nf/bbf-olt-vomci:nf-client/bbf-olt-vomci:initiate/" +
              "bbf-olt-vomci:remote-server" {
        description "only one remote server supported";
        deviate add {
            max-elements 1;
        }
    }

    deviation "/if:interfaces/if:interface/bbf-xponvani:v-ani/bbf-olt-vomci:vomci-onu/bbf-olt-vomci:vomci-function/bbf-olt-vomci:remote-endpoint" {
        deviate replace {
            type leafref {
                path '/bbf-olt-vomci:remote-nf/bbf-olt-vomci:nf-client/bbf-olt-vomci:initiate/bbf-olt-vomci:remote-server/bbf-olt-vomci:name';
            }
        }
    }
}
