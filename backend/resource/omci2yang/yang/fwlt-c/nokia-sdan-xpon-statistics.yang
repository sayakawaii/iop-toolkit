module nokia-sdan-xpon-statistics {
    yang-version 1.1;
    namespace "http://www.nokia.com/Fixed-Networks/BBA/yang/"
        + "nokia-sdan-xpon-statistics";

    prefix nokia-xpon-stats;

    import ietf-yang-types {
        prefix yang;
    }

    import ietf-interfaces {
        prefix if;
    }

    import bbf-xpon-if-type {
        prefix bbf-xponift;
    }

    organization
        "Nokia";

    contact
        "Comments or questions about this Nokia YANG module should be
        directed to <mailto:isam.yang@nokia.com>.";

    description
        "This module contains a collection of YANG definitions for
        supporting Nokia specific requirements as applicable to its
        access network equipment.

        This specification is published by Nokia under Non-Disclosure
        Agreement(s) (NDA) with specific parties and has to be
        considered as Confidential Information as defined in such NDA.
        Nokia reserves the right to revise this document for any
        reason, including but not limited to conformity with standards
        promulgated by various agencies, utilisation of advances in
        the state of the technical areas, or the reflection of changes
        in the design of any equipment, techniques, or procedures
        described or referred to herein.

        The product specifications and other technical or performance
        information contained herein are subject to change without
        notice.  Updates of this document will be issued under the
        above NDA's.

        Nokia makes no representation or warranty, expressed or
        implied, with respect to the sufficiency, accuracy, or utility
        of any information or opinion contained herein.  Nokia
        expressly advises that any use of for any purpose or reliance
        upon this technical reference is at the risk of the user and
        that Nokia shall not be liable for any damage or injury
        incurred by any person arising out of the sufficiency,
        accuracy, or utility of any information or opinion contained
        herein.

        This document is not to be construed as a suggestion to any
        manufacturer to modify or change any of its products, nor does
        this document represent any commitment by Nokia to sell or
        purchase any product.  Nothing contained herein shall be
        construed as conferring by implication, estoppel, or otherwise
        any license or right under any patent, whether or not the use
        of any information herein necessarily employs an invention of
        any existing or later issued patent.

        Nokia reserves the right not to offer any or all of these
        products and to withdraw any or all of them at any future
        time.

        Copyright (C) 2021, Nokia.  All Rights Reserved.";

    revision 2021-05-20 {
            description
                "Initial revision";
            reference
                "Nokia specific";
        }

    grouping
        xpon-specific-counters {
            description
                "xPON specific statistics counters.";

            leaf out-incidental-broadcast-gem-port-bytes{
                type yang:counter64;
                description
                    "The number of bytes transmitted on the incidental
                    broadcast GEM Port on the channel termination.";
            }

            leaf out-incidental-broadcast-gem-port-packets{
                type yang:counter64;
                description
                    "The number of packets transmitted on the
                    incidental broadcast GEM Port on the channel
                    termination.";
            }

            leaf out-incidental-broadcast-gem-port-dropped-bytes{
                type yang:counter64;
                description
                    "The number of outbound bytes that could not be
                    transmitted on the incidental broadcast GEM Port
                    on the channel termination, for whatever reason,
                    e.g.  due to errors or lack of buffer space.";
            }

            leaf out-incidental-broadcast-gem-port-dropped-packets{
                type yang:counter32;
                description
                    "The number of outbound packets that could not be
                    transmitted on the incidental broadcast GEM Port
                    on the channel termination, for whatever reason,
                    e.g.  due to errors or lack of buffer space.";
            }

            leaf out-multicast-gem-port-bytes{
                type yang:counter64;
                description
                    "The number of bytes transmitted on all multicast
                    GEM Ports on the channel termination.";
            }

            leaf out-multicast-gem-port-packets{
                type yang:counter64;
                description
                    "The number of packets transmitted on all
                    multicast GEM Ports on the channel termination.";
            }

            leaf out-multicast-gem-port-dropped-bytes{
                type yang:counter64;
                description
                    "The number of outbound bytes that could not be
                    transmitted on all multicast GEM ports on the
                    channel termination, for whatever reason, e.g.
                    due to errors or lack of buffer space.";
            }

            leaf out-multicast-gem-port-dropped-packets{
                type yang:counter32;
                description
                    "The number of outbound packets that could not be
                    transmitted on all multicast GEM ports on the
                    channel termination, for whatever reason, e.g.
                    due to errors or lack of buffer space.";
            }

            leaf out-unicast-gem-port-bytes{
                type yang:counter64;
                description
                    "The number of bytes transmitted on all unicast
                    GEM Ports on the channel termination.";
            }

            leaf out-unicast-gem-port-packets{
                type yang:counter64;
                description
                    "The number of packets transmitted on all unicast
                    GEM Ports on the channel termination.";
            }

            leaf out-unicast-gem-port-dropped-bytes{
                type yang:counter64;
                description
                    "The number of outbound bytes that could not be
                    transmitted on all unicast GEM Ports on the
                    channel termination, for whatever reason, e.g.
                    due to errors or lack of buffer space.";
            }

            leaf out-unicast-gem-port-dropped-packets{
                type yang:counter32;
                description
                    "The number of outbound packets that could not be
                    transmitted on all unicast GEM Ports on the
                    channel termination, for whatever reason, e.g.
                    due to errors or lack of buffer space.";
            }
        }

    augment '/if:interfaces-state/if:interface/if:statistics' {
        when " derived-from-or-self(../if:type, "
            + "'bbf-xponift:channel-termination')";
        description
            "This augment defines statistics data specific to xPON.";
        container xpon {
            description
                "Statistic counters specific to xPON.";
            uses
                xpon-specific-counters;
        }
    }
}
