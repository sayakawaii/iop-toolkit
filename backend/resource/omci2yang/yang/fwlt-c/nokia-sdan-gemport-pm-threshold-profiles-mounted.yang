module nokia-sdan-gemport-pm-threshold-profiles-mounted {
  yang-version 1.1;
  namespace "http://www.nokia.com/Fixed-Networks/BBA/yang/"
          + "nokia-sdan-gemport-pm-threshold-profiles-mounted";
  prefix nokia-gemport-pm-tca-prof-mounted;
  import bbf-yang-types {
    prefix bbf-yang;
  }
  import nokia-yang-types-mounted {
    prefix nok-typ-mounted;
  }
  import nokia-hardware-profiles-mounted {
    prefix nokia-hw-prof-mounted;
  }
  import nokia-sdan-hardware-pm-threshold-profiles-mounted {
    prefix nokia-hw-pm-threshold-prof-mounted;
  }
  import bbf-fiber-onu-emulated-mount {
    prefix onu;
  }
  organization
    "Nokia";
  contact
    "Comments or questions about this Nokia YANG module should be
     directed to <mailto:isam.yang@nokia.com>.";
  description
    "This module contains a collection of YANG definitions for
     supporting Nokia specific requirements as applicable to its
     access network equipment.
     This module, in particular, augments the performance monitoring threshold
     profiles with data that allows you to configure thresholding values for
     performance data associated with Ethernet counters.
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.
     The product specifications and other technical or performance
     information contained herein are subject to change without
     notice. Updates of this document will be issued under the above
     NDA's.
     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
     Nokia reserves the right not to offer any or all of these
     products and to withdraw any or all of them at any future time.
     Copyright (C) 2022, Nokia. All Rights Reserved.";
  revision 2022-12-22 {
    description
      "TCA profile support for gemport performance monitoring counters";
    reference
      "ITU-T G.988 OMCI specification";
  }
  identity gemport-pm-tca-alert {
    description 
      "Indicates which Gemport performance monitoring TCA element has reached the configured
       threshold value within the current interval"; 
  }
  identity gemport-pm-tca-encryption-key-errors {
    base gemport-pm-tca-alert;
    description
      "Indicates that the gemport encryption key errors has reached the configured threshold value
       within the current interval";
  }
  augment "/onu:onus/onu:onu/onu:root/nokia-hw-prof-mounted:tca-profiles/nokia-hw-pm-threshold-prof-mounted:pm-profiles" {
    description "augment pm profiles";
    list gemport-tca-profile {
      key "name";
      description
        "TCA profile to configuire gemport perforamnce monitoring counters";
      leaf name {
        type nok-typ-mounted:nokia-string-ascii64;
        description
          "Indicates name of the profle that can be applied to gemport performance
          monitoring counters";
      }
      leaf encryption-key-errors-threshold {
        type bbf-yang:performance-counter64;
        description
          "Threshold value for the number of GEM frames with errorneous key indexes.
           When the number of gemport encryption key errors crosses the threshold a TCA is raised";
      }
    }
  }
}
