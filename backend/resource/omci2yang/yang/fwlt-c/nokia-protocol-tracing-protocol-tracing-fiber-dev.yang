module nokia-protocol-tracing-protocol-tracing-fiber-dev {
  yang-version 1.1;

  namespace "http://www.nokia.com/Fixed-Networks/BBA/yang/"
          + "nokia-protocol-tracing-protocol-tracing-fiber-dev";

  prefix nokia-protocol-tracing-fiber-dev;

  import ietf-interfaces {
    prefix if;
  }

  import nokia-protocol-tracing {
    prefix npt;
  }
    
  import bbf-if-type {
    prefix bbfift;
  }
  
  import iana-if-type {
    prefix ianaift;
  }
  
  import bbf-interface-usage {
    prefix bbf-if-usg;
  }

  import bbf-sub-interfaces {
    prefix bbf-subif;
  }
  
  import bbf-vlan-sub-interface-vector {
    prefix bbf-vsi-vctr;
  } 
 
  import bbf-vlan-sub-interface-vector-usage {
    prefix bbf-vsi-vctr-usg;
  }

  import bbf-xpon-if-type {
    prefix bbf-xponift;
  }

  import tailf-common { prefix tailf; }
  
  organization
    "Nokia";

  contact
    "Comments or questions about this Nokia YANG module should be
     directed to <mailto:isam.yang@nokia.com>.";

  description
    "This module contains a collection of YANG definitions for
     supporting Nokia specific requirements as applicable to its
     access network equipment.

     Specifically, this module provides restrictions (=deviations) for
     the implementation in the Lightspan.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2026-02-02 {
      description
          "Enable MLD from fiber boards.";
      reference
          "Nokia specific";
  }
  
  revision 2025-07-07 {
    description "";
    reference "Nokia specific";
  }
  
  revision 2024-01-11 {
    description
      "Disable MLD from fiber boards.";
    reference
      "Nokia specific";
  }

  revision 2023-08-07 {
    description
      "Initial revision.";
    reference
      "Nokia specific";
  }

  tailf:annotate /npt:protocol-tracing {
  }
  
  deviation "/npt:protocol-tracing/npt:session/npt:interface"  {
    deviate add{
      must "not"
       + "("
       + " ("
       + "    /if:interfaces/if:interface[if:name = current()]/if:type = 'bbfift:vlan-sub-interface' and "
       + "    (boolean(/npt:protocol-tracing/npt:session[npt:interface = /if:interfaces/if:interface[if:name = current()]/bbf-subif:subif-lower-layer/bbf-subif:interface]))"
       + " )"
       + " and "
       + " ("
       + "  ("
       + "    /npt:protocol-tracing/npt:session[npt:name = current()/../name][bit-is-set(npt:protocol-selector,'dhcp')]  and "
       + "    /npt:protocol-tracing/npt:session[npt:interface = /if:interfaces/if:interface[if:name = current()]/bbf-subif:subif-lower-layer/bbf-subif:interface][bit-is-set(npt:protocol-selector,'dhcp')]"
       + "  )"
       + "  or"
        + "  ("
       + "    /npt:protocol-tracing/npt:session[npt:name = current()/../name][bit-is-set(npt:protocol-selector,'dhcpv6')]  and "
       + "    /npt:protocol-tracing/npt:session[npt:interface = /if:interfaces/if:interface[if:name = current()]/bbf-subif:subif-lower-layer/bbf-subif:interface][bit-is-set(npt:protocol-selector,'dhcpv6')]"
       + "  )"
       + "  or"
       + "  ("
       + "    /npt:protocol-tracing/npt:session[npt:name = current()/../name][bit-is-set(npt:protocol-selector,'igmp')]  and "
       + "    /npt:protocol-tracing/npt:session[npt:interface = /if:interfaces/if:interface[if:name = current()]/bbf-subif:subif-lower-layer/bbf-subif:interface][bit-is-set(npt:protocol-selector,'igmp')]"
       + "  )"
       + "  or"
        + "  ("
       + "    /npt:protocol-tracing/npt:session[npt:name = current()/../name][bit-is-set(npt:protocol-selector,'pppoe')]  and "
       + "    /npt:protocol-tracing/npt:session[npt:interface = /if:interfaces/if:interface[if:name = current()]/bbf-subif:subif-lower-layer/bbf-subif:interface][bit-is-set(npt:protocol-selector,'pppoe')]"
       + "  )"
       + "  or"
       + "  ("
       + "    /npt:protocol-tracing/npt:session[npt:name = current()/../name][bit-is-set(npt:protocol-selector,'arp')]  and "
       + "    /npt:protocol-tracing/npt:session[npt:interface = /if:interfaces/if:interface[if:name = current()]/bbf-subif:subif-lower-layer/bbf-subif:interface][bit-is-set(npt:protocol-selector,'arp')]"
       + "  )"
       + "  or"
       + "  ("
       + "    /npt:protocol-tracing/npt:session[npt:name = current()/../name][bit-is-set(npt:protocol-selector,'mld')]  and "
       + "    /npt:protocol-tracing/npt:session[npt:interface = /if:interfaces/if:interface[if:name = current()]/bbf-subif:subif-lower-layer/bbf-subif:interface][bit-is-set(npt:protocol-selector,'mld')]"
       + "  )"
       + "  or"
       + "  ("
       + "    /npt:protocol-tracing/npt:session[npt:name = current()/../name]/npt:protocol-selector = 'all' or "
       + "    /npt:protocol-tracing/npt:session[npt:interface = /if:interfaces/if:interface[if:name = current()]/bbf-subif:subif-lower-layer/bbf-subif:interface]/npt:protocol-selector = 'all' "
       + "  )"
       + " )"
       + ")"
       {
         error-message "A tracing session on an interface of type vlan-sub-interface has overlapping protocol-selector with a tracing session on lower layer interface of that vlan-sub-interface ";
         description   "A tracing session on an interface of type vlan-sub-interface has overlapping protocol-selector with a tracing session on lower layer interface of that vlan-sub-interface";  
      }
    }
  }


deviation "/npt:protocol-tracing/npt:session/npt:interface"  {
    deviate add{
       must  "("
           + " /if:interfaces/if:interface[if:name = current()]/if:type = 'bbf-xponift:olt-v-enet' "
           + ")"
           + "or"
           + "("
           + " /if:interfaces/if:interface[if:name = current()]/if:type = 'ianaift:ethernetCsmacd' and"
           + " /if:interfaces/if:interface[if:name = current()]/bbf-if-usg:interface-usage/bbf-if-usg:interface-usage = 'user-port'"
           + ")"
           + "or"
           + "("
           + " /if:interfaces/if:interface[if:name = current()]/if:type = 'bbfift:vlan-sub-interface' "
           + " and "
           + " ("
           + "  /if:interfaces/if:interface[if:name = current()]/bbf-if-usg:interface-usage/bbf-if-usg:interface-usage = 'user-port' or"
           + "  /bbf-vsi-vctr:vsi-vector-profiles/bbf-vsi-vctr:vsi-vector-profile[bbf-vsi-vctr:name = /if:interfaces/if:interface[if:name = current()]/bbf-vsi-vctr:vector-profile]/"
           + "  bbf-vsi-vctr-usg:interface-usage/bbf-vsi-vctr-usg:interface-usage = 'user-port'"
           + " )"
           + ")"
           + "or"
           + "("
           + " /if:interfaces/if:interface[if:name = current()]/if:type = 'bbfift:vlan-sub-interface' " 
           + " and "
           + " ("
           + "  ("
           + "   /if:interfaces/if:interface[if:name = current()]/bbf-if-usg:interface-usage/bbf-if-usg:interface-usage = 'inherit' and"
           + "   /if:interfaces/if:interface[/if:interfaces/if:interface[if:name = current()]/bbf-subif:subif-lower-layer/bbf-subif:interface]/bbf-if-usg:interface-usage/bbf-if-usg:interface-usage = 'user-port'"
           + "  )"
           + "  or"
           + "  ("
           + "   /bbf-vsi-vctr:vsi-vector-profiles/bbf-vsi-vctr:vsi-vector-profile[bbf-vsi-vctr:name = /if:interfaces/if:interface[if:name = current()]/bbf-vsi-vctr:vector-profile]/"
           + "   bbf-vsi-vctr-usg:interface-usage/bbf-vsi-vctr-usg:interface-usage = 'inherit' and "
           + "   /if:interfaces/if:interface[/if:interfaces/if:interface[if:name = current()]/bbf-subif:subif-lower-layer/bbf-subif:interface]/bbf-if-usg:interface-usage/bbf-if-usg:interface-usage = 'user-port'"
           + "  )"
           + " )"
           + ")" 
           + "or"
           + "("
           + " ("
           + "  /npt:protocol-tracing/npt:session[npt:name = current()/../name][bit-is-set(npt:protocol-selector,'igmp')] or "
           + "  /npt:protocol-tracing/npt:session[npt:name = current()/../name][bit-is-set(npt:protocol-selector,'mld') ] "
           + " )"
           + " and "
           + " ("
           + "  not (/npt:protocol-tracing/npt:session[npt:name = current()/../name][bit-is-set(npt:protocol-selector,'dhcp' )])  and "
           + "  not (/npt:protocol-tracing/npt:session[npt:name = current()/../name][bit-is-set(npt:protocol-selector,'pppoe')])  and " 
           + "  not (/npt:protocol-tracing/npt:session[npt:name = current()/../name][bit-is-set(npt:protocol-selector,'arp')])    and "
           + "  not (/npt:protocol-tracing/npt:session[npt:name = current()/../name][bit-is-set(npt:protocol-selector,'dhcpv6')]) "
           + " )"
           + " and " 
           + " /if:interfaces/if:interface[if:name = current()]/if:type = 'bbfift:vlan-sub-interface' "
           + " and "
           + " ("
           + "  /if:interfaces/if:interface[if:name = current()]/bbf-if-usg:interface-usage/bbf-if-usg:interface-usage = 'network-port' or"
           + "  ("
           + "   /if:interfaces/if:interface[if:name = current()]/bbf-if-usg:interface-usage/bbf-if-usg:interface-usage = 'inherit' and"
           + "   /if:interfaces/if:interface[/if:interfaces/if:interface[if:name = current()]/bbf-subif:subif-lower-layer/bbf-subif:interface]/bbf-if-usg:interface-usage/bbf-if-usg:interface-usage = 'network-port'"
           + "  )"           
           + " )"
           + ")"
           {
        error-message "Protocol tracing at user side only supported for interface types olt-v-enet, vlan-sub-interface. "
           +          "Protocol tracing at network side only supported for protocols igmp,mld and interface type vlan-sub-interface. "
           +          "Interface-usage value determines user or network side. ";
        description "Protocol tracing only supported on specific interface types and protocol-selector values";
      }
    }

  }
}
