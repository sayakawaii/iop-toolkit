module bbf-xponvani-onu-authentication-groupings {
  yang-version 1.1;
  namespace "urn:bbf:yang:bbf-xponvani-onu-authentication-groupings";
  prefix bbf-xponvani-onu-authg;

  import bbf-yang-types {
    prefix bbf-yang;
  }
  import bbf-xpon-onu-authentication-types {
    prefix bbf-xpon-onu-autht;
  }
  import bbf-xpon-onu-authentication-features {
    prefix bbf-xpon-onu-authf;
  }

  organization
    "Broadband Forum <https://www.broadband-forum.org>
     Fiber Access Networks Work Area";
  contact
    "Comments or questions about this Broadband Forum YANG module
     should be directed to <mailto:info@broadband-forum.org>.

     Editor:      Robert Peschi, Nokia

     Editor:      Kevin Noll, Vecima

     PS Leader:   Joey Boyd, Adtran

     WA Director: Marta Seda, Calix";
  description
    "This module contains a collection of YANG definitions for
     supporting the Broadband Forum requirements on management of
     ITU-T Passive Optical Network (PON) interfaces as defined in
     ITU-T G.984.x, G.987.x, ITU-T G.989.x and ITU-T G.9807.x. As
     such, this module is specific to access network equipment (e.g.,
     BBF-specified Access Nodes and FTTdp DPUs).

     Specifically, this module defines groupings that can be used
     for Virtual Access Network Interface (vANI) data nodes about
     Optical Network Unit (ONU) authentication and the decision
     to apply an OMCI function.

     Copyright (c) 2018-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i2a1; see
     the TR itself for full legal notices.";

  revision 2023-06-21 {
    description
      "Issue 2 Amendment 1.
       * Approval Date:    2023-06-21.
       * Publication Date: 2023-06-21.";
    reference
      "TR-385i2a1: ITU-T PON YANG Modules
               <https://www.broadband-forum.org/technical/download/
                        TR-385_Issue-2_Amendment-1.pdf>";
  }

  grouping v-ani-onu-authentication {
    description
      "Virtual Access Network Interface (vANI) configuration
       data for Optical Network Unit (ONU) authentication and
       decision for eOMCI or vOMCI management mode.";
    leaf onu-name {
      if-feature "bbf-xpon-onu-authf:"
               + "configurable-onu-name";
      type bbf-yang:string-ascii64;
      description
        "The name of the Optical Network Unit (ONU) device
         corresponding to this virtual Access Network
         Interface (vANI). This 'onu-name' could be used as
         means to help correlating the ONU authentication
         function with the ONU management function.
         It could be used as a direct ONU key in the (ONU) device
         aggegation function in the management plane and/or in
         the Optical Line Termination (OLT), as for instance
         in TR-489 for Scenarios 2, 3 or 4.";
      reference
        "TR-489, section 6.2 and section 8.2, R-OLT_1, R-OLT_6,
         R-OLT_7, R-OLT_9 and R-OLT_10";
    }
    leaf expected-loid {
      if-feature "bbf-xpon-onu-authf:"
               + "can-retrieve-loid-pre-auth";
      type string {
        length "1..24";
      }
      description
        "The Logical ONU ID (LOID) value that the Optical Line
         Termination (OLT) expects to retrieve from the Optical
         Network Unit (ONU).
         It is a string that has been assigned to the subscriber
         by the Management Plane, entered into and stored in
         non-volatile storage at the ONU.
         The LOID could be useful in identifying a particular ONU
         installed at a particular location, for instance in an
         failed ONU replacement scenario.";
      reference
        "ITU-T G.988 Clause 9.1.1
         TR-489, section 4.1.1 and section 8.2, R-OLT_1";
    }
    leaf expected-onu-management-mode {
      if-feature "bbf-xpon-onu-authf:"
               + "configurable-expected-onu-management-mode";
      type identityref {
        base bbf-xpon-onu-autht:onu-management-config-base;
      }
      description
        "Indicates to the OLT whether the Optical Network Unit
         (ONU) corresponding to this virtual Access Network
         Interface (vANI) must be managed via an OMCI function
         embedded in the OLT (eOMCI) or by an OMCI function
         virtualized in the Management Plane (vOMCI).";
      reference
        "TR-489, section 6.2.1";
    }
  }

  grouping v-ani-onu-authentication-state {
    description
      "Virtual Access Network Interface (vANI) state
       data for Optical Network Unit (ONU) authentication and
       decision for eOMCI or vOMCI management mode.";
    leaf detected-loid {
      if-feature "(bbf-xpon-onu-authf:"
               + "can-retrieve-loid-pre-auth or "
               + "bbf-xpon-onu-authf:"
               + "support-onu-authentication-report)";
      type string {
        length "1..24";
      }
      description
        "The Logical Identifier (LOID) value currently used
         by an Optical Network Unit (ONU) that the Optical
         Line Termination (OLT) has successfully authenticated
         and has associated to this vANI. The OLT could directly
         retrieve the LOID from the ONU (if able to do so before
         the ONU is authenticated) or indirectly from
         the Management Plane reporting the ONU authentication
         results).
         This data node is not present if the ONU is not using
         any LOID or if the OLT lacks the capability to
         query the ONU for its LOID before the ONU is authenticated
         and didn't receive it either in an ONU authentication report
         from the Management Plane.
         The LOID may be useful in identifying a particular ONU
         installed at a particular location, for instance in an
         failed ONU replacement scenario.";
      reference
        "ITU-T G.988 Clause 9.1.1
         TR-489, section 8.2, R-OLT_11";
    }
    leaf determined-onu-management-mode {
      type identityref {
        base bbf-xpon-onu-autht:onu-management-state-base;
      }
      description
        "The Optical Network Unit (ONU) management mode determined
         by the Optical Line Termination (OLT) distinguishing between
         eOMCI and vOMCI, or otherwise indicating an inconsistency or
         error condition.

         Note that this may only be present when the corresponding
         ONU is present on a channel termination and has been
         successfully authenticated.";
      reference
        "TR-489, section 6.1 and section 8.2, R-OLT_6, R-OLT_7,
         R-OLT_8 and R-OLT_10";
    }
  }
}
