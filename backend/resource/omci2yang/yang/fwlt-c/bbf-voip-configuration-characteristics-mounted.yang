submodule bbf-voip-configuration-characteristics-mounted {
  yang-version 1.1;
  belongs-to bbf-voip-configuration-mounted {
    prefix bbf-voip-config-mounted;
  }
  
  import bbf-yang-types {
    prefix bbf-yang;
  }
  
  import ietf-inet-types {
    prefix inet;
	reference
      "RFC 6991: Common YANG Data Types.";
  }

  import bbf-fiber-onu-emulated-mount {
     prefix onu;
  }

  import nokia-template-common {
    prefix template-common;
  }   
    
  
  include bbf-voip-file-authentication-settings-mounted;
  
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains a collection of YANG definitions for
     managing the Voip configuration, such as protocol, configuration method.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2020-03-06 {
    description
      "Initial revision.
       * Approval Date:    see revision date above.
       * Publication Date: 2020-03-06.";
    reference
      " ";
  }
  
  grouping config-file-failure {
    leaf failure-reason {
	  type enumeration {
        enum no-failure {
          value 1;
          description
            "Download succeeded.";
        }
		enum authentication-failure {
          value 2;
          description
            "Authentication failure.";
        }
		enum file-notfound {
          value 3;
          description
            "The file was not found. The file name is wrong or
			 the path is wrong.";
        }
		enum file-corrupt {
          value 4;
          description
            "The file is corrupt.";
        }
	  }
    }
	leaf failure-text {
	  when "../bbf-voip-config-mounted:failure-reason != 'bbf-voip-config-mounted:no-failure'" {
        description
          "Only valid when there is a failure.";
      }
    type string;
    description
      "A text string indicating the reason for the failure when
       either no defined reason exists or additional information
       is available beyond the definition of the reason.";
    }
  }
  
  grouping config-file-characteristics {
  	leaf config-file-name {
      type bbf-yang:name-string;
	  /* mandatory true; */
      description
        "The name of the Voip configuration 
		 file.";
    }
    leaf config-file-version {	       
      type string {length "1..32";}
      description
        "The version of the Voip configuration file.";
	}
	description
	  "Characteristics of the Voip configuration file.";
  }
  
  grouping config-file-download-characteristics { 
  	description
	  "Download characteristics of the Voip configuration 
	   file.";
	leaf ftp-server {
	  type inet:ip-address; 
	  description
	    "IP-address of the ftp-server.";
	} 
	uses file-authentication-settings;	
  }


 augment '/onu:onus/onu:onu/onu:root' {
  when "derived-from-or-self(../onu:usage, 'template-common:node-actual-usage') or "
       + "derived-from-or-self(../onu:usage, 'template-common:node-template-usage')" {
     description
       "it should be a node-actual-usage or node-template-usage ONU";
  } 	  
  container voip-configuration-characteristics {
    description
	  "The Voip Configuration.";
    leaf signaling-protocol {
	  type enumeration {
	    enum sip {
		  value 1;
		  description 
		    "The Session Initiation Protocol is used.";
		}	
		enum H248 {
		  value 2;
		  description 
		    "The H.248 protocol is used.";
		}
		enum mgcp {
		  value 3;
		  description 
		    "The Media Gateway Control Protocol is used.";
		}		
	  }	
	  default sip;
      description
        "The signaling protocol to set up a Voip Session.";	  
	}
	leaf configuration-method {
	  type enumeration {
	    enum omci {
	      value 1;
	      description
	        "Voip configuration via OMCI.";
	    }
        enum sip-config {
          value 2;
          description 
            "Configuration via the SIP Config framework, as 
	         defined by IETF RFC 6080).";	
        }
		enum tr-104 {
		  value 3;
		  description
		    "Configuration of VOIP via service model TR-104 with
			 root model TR-098 or root model TR-181.";
		}
	  }
      default omci;
	  description
	    "The Voip configuration methods.";
	}
	container voip-omci-config-file {
	when "../bbf-voip-config-mounted:configuration-method = 'omci'";
	  description
	    "Voip configuration via OMCI in combination with an
	     additional Voip configuration file embedded or to be
		 retrieved from an ftp server. This file contains be HW 
		 specific information, vendor specific information.";
	  uses config-file-characteristics;
	
	  action ftp-download-file {
        description
          "Downloaded the Voip configuration file from an FTP 
		   server.";     
        input {
          uses config-file-characteristics;
          uses file-authentication-settings;	  
	    }   
	    output {
	      uses config-file-failure;
	   }
      }	
	}
	leaf voip-config-state {
	  config false;
	  type enumeration {
	    enum inactive {
	      value 0;
		  description
		    "The configuration retrieval has not been attempted.";
        }
	    enum active {
	      value 1;
		  description
		    "The configuration was retrieved.";
        }
	    enum initializing {
	      value 2;
		  description
		    "The configuration is now being retrieved.";
        }
	    enum failed {
	      value 3;
		  description
		    "The configuration retrieval process failed.";
        }
	  }
	  description
	    "Voip configuration state.";
	}	
  }		
 }
}
