module nokia-sdan-hardware-cpu-performance-management-frommounted {
  yang-version 1.1;
  namespace "http://www.nokia.com/Fixed-Networks/BBA/yang/"
          + "nokia-sdan-hardware-cpu-performance-management-frommounted";
  prefix nokia-cpu-pm-mgnt-frommounted;

  import bbf-fiber-onu-emulated-mount {
    prefix onu;
  }
  import ietf-hardware-frommounted {
    prefix hw-frommounted;
  }


  organization
    "Nokia";
  contact
    "Comments or questions about this Nokia YANG module should be
     directed to <mailto:isam.yang@nokia.com>.";
  description
    "This module contains a collection of YANG definitions for
     supporting Nokia specific requirements as applicable to its
     access network equipment.

     Specifically, this module augments the hardware model with data
     that supports configuring performance monitoring and thresholding.
     Also augments the hardware model with performance monitoring
     data of a CPU component.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2025-06-04 {
    description
      "PM counter group support for CPU";
    reference
      "Nokia specific for EPIC BBN-107831";
  }

  revision 2022-05-16 {
    description
      "Augments hardware componenet with CPU as class to attach TCA profiles.";
    reference
      "Nokia specific.";
  }


  augment "/onu:onus/onu:onu/onu:fromroot/hw-frommounted:hardware/hw-frommounted:component" {
    description "augment hw component cpu";
    container performance {
      presence "If container is not present, CPU performance monitoring is disabled.
                If container is present CPU performance monitoring is disabled or enabled
                depending on the value of 'enable' leaf.";
      description
        "Performance parameters.";
      leaf enable {
        type boolean;
        description
          "If true, enables performance monitoring on this hardware component.
           The performance data will be available under
           '/onu:onus/onu:onu/onu:fromroot/hw-frommounted:hardware-state/hw-frommounted:component/'
           for 15 minute and, if supported, 24 hour current and
           historic intervals.
           If false, then there are no performance data available
           on this hardware component.";
      }
      leaf cpu-tca-profile {
        type string;
        description
          "Reference to a CPU threshold profile. Allowes to configure threshold values
           for CPU performance monitoring data. TCA is disabled when no profile is
           referenced. This has no effect when performance monitoring is disabled";
      }
      leaf memory-tca-profile {
        type string;
        description
          "Reference to a memory threshold profile. Allowes to configure threshold values
           for memory performance monitoring data. TCA is disabled when no profile is
           referenced. This has no effect when performance monitoring is disabled";
      }
      leaf-list cpu-mem-util-group {
	type cpu-mem-util-group-type;
	description
	      "Performance monitoring group type to enable or disable
	      specific performance monitoring counters";
      }
    }
  }
  typedef cpu-mem-util-group-type {
      type enumeration {
          enum "cpu-util-pm" {
              description
                "This enables the performance monitoring for cpu utilization in hardware component.
                When this PM counter group is enabled, the current and history performance data for below xpaths are enabled
                    - hardware-state/component/performance/current/system-load
                    - hardware-state/component/performance/history/system-load";
          }
          enum "mem-usage-pm" {
              description
                "This enables the performance monitoring for memory usage in hardware component.
                When this PM counter group is enabled, the current and history performance data for below xpaths are enabled
                    - hardware-state/component/performance/current/memory-usage
                    - hardware-state/component/performance/history/memory-usage";
          }
      }
      description
	"cpu memory util pm group type";
  }
}
