module bbf-qos-policies-mounted {
  yang-version 1.1;
  namespace "urn:bbf:yang:bbf-qos-policies-mounted";

  prefix bbf-qos-pol-mounted;

  import ietf-interfaces-mounted {
    prefix if-mounted;
  }

  import iana-if-type-mounted {
    prefix ianaift-mounted;
  }

  import bbf-if-type-mounted {
    prefix bbfift-mounted;
  }

  import bbf-yang-types {
    prefix bbf-yang;
  }

  import bbf-qos-classifiers-mounted {
    prefix bbf-qos-cls-mounted;
  }

  import bbf-fiber-onu-emulated-mount {
     prefix onu;
  }

  import nokia-template-common {
    prefix template-common;
  }
           
  import nokia-interface-identities-mounted {
    prefix nokia-if-id-mounted;
  } 
 
  organization
    "Broadband Forum <https://www.broadband-forum.org>
     Common YANG Project Stream";

  contact
    "Comments or questions about this Broadband Forum YANG module
     should be directed to <mailto:help@broadband-forum.org>.

     Editor:      Joey Boyd, ADTRAN
                  <mailto:joey.boyd@adtran.com>

     Editor:      Ludwig Pauwels, Nokia
                  <mailto:ludwig.pauwels@nokia.com>

     PS Leader:   Michael Shaffer, Nokia
                  <mailto:michael.shaffer@nokia.com>

     PS Leader:   William Lupton, Broadband Forum
                  <mailto:wlupton@broadband-forum.org>";

  description
    "This module contains a collection of YANG definitions for 
     supporting the Broadband Forum requirements on the management of
     Quality of Service (QoS) as applicable to access network 
     equipment. As such, this module is specific to access network 
     equipment (e.g., BBF-specified Access Nodes and FTTdp DPUs).

     Specifically, this module contains a collection of policies 
     applied to packets. 

     Copyright (c) 2017, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2024-05-22 {
    description
      "Supported QoS policy profiles for moca-uni.";
    reference
      "Nokia specific EPIC BBN-729";
  }

  revision 2017-05-08 {
    description
      "Initial revision.
       * Approval Date:    see revision date above.
       * Publication Date: 2017-06-02.";
    reference
      "TR-383: Common YANG Modules
               <https://www.broadband-forum.org/technical/download/
                        TR-383.pdf>";
  }


augment '/onu:onus/onu:onu/onu:root' {
  when "derived-from-or-self (../onu:usage, 'template-common:node-actual-usage') or
        derived-from-or-self (../onu:usage, 'template-common:node-template-usage')" {
     description
       "it should be a node-actual-usage or node-from-template-usage ONU for qos policies configuration";
  }

  container policies {
    description
      "List of policy templates.";

    list policy {
      key "name";
      description
        "Policy template.";

      leaf name {
        type bbf-yang:string-ascii64;
        description
          "Name of the policy.";
      }

      leaf description {
        type bbf-yang:string-ascii64-or-empty;
        description
          "Description of the policy.";
      }

      list classifiers {
//        if-feature "bbf-qos-cls:classifier-profiles";
        key "name";
        ordered-by user;
        description
          "Provides a lists of classifiers which are evaluated in 
           order as specified by the user. When a classifier is 
           matched, no other classifiers are evaluated.";

        uses bbf-qos-cls-mounted:classifier-entry-ref;
      }
    }
  }
}

  grouping policy-entry-ref {
    description
      "A reference to a policy entry.";

    leaf name {
      type leafref {
        path '../../../../bbf-qos-pol-mounted:policies/bbf-qos-pol-mounted:policy/bbf-qos-pol-mounted:'
           + 'name';
      }
      description
        "The name of the referenced policy entry.";
    }
  }

augment '/onu:onus/onu:onu/onu:root' {
  container qos-policy-profiles {
    description
      "This container provides a framework for QoS policy profile 
       configuration.";

    list policy-profile {
      key "name";
      description
        "A list of policy-profiles.";

      leaf name {
        type bbf-yang:string-ascii64;
        description
          "Name of the QoS policy profile.";
      }

      list policy-list {
        key "name";
        ordered-by user;
        description
          "Provides ordered lists of policies for the ingress and for 
           the egress direction.

           The definition is that all policies are executed in the  
           order of the list. The output of one policy is used as 
           input for the next policy.";

        uses policy-entry-ref;
      }
    }
  }
}


  augment '/onu:onus/onu:onu/onu:root/if-mounted:interfaces/if-mounted:interface' {
    when
      "derived-from-or-self(if-mounted:type, 'ianaift-mounted:ethernetCsmacd') or
       derived-from-or-self(if-mounted:type, 'ianaift-mounted:ieee8023adLag') or
       derived-from-or-self(if-mounted:type, 'ianaift-mounted:ptm') or
       derived-from-or-self(if-mounted:type, 'bbfift-mounted:vlan-sub-interface') or
       derived-from-or-self(if-mounted:type, 'nokia-if-id-mounted:moca-uni')" {
      description
        "Interfaces that can have QoS policy profiles assigned.";
    }

    description
      "Assigns a group of policies to an interface.";

    leaf ingress-qos-policy-profile {
      type leafref {
        path '../../../bbf-qos-pol-mounted:qos-policy-profiles/bbf-qos-pol-mounted:policy-'
            + 'profile/bbf-qos-pol-mounted:name';
      }
      description
        "A reference to a Qos policy profile. The profile is to be 
         applied to incoming packets.";
    }

    leaf egress-qos-policy-profile {
      type leafref {
        path '../../../bbf-qos-pol-mounted:qos-policy-profiles/bbf-qos-pol-mounted:policy-'
            + 'profile/bbf-qos-pol-mounted:name';
      }
      description
        "A reference to a Qos policy profile. The profile is to be 
         applied to outgoing packets.";
    }
  }
}
