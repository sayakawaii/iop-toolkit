module nokia-sdan-xpon-channel-partition {
    yang-version 1.1;
    namespace "http://www.nokia.com/Fixed-Networks/BBA/yang/"+
        "nokia-sdan-xpon-channel-partition";

    prefix nokia-sdan-xpon-channel-partition;

    import ietf-interfaces {
        prefix if;
    }

    import bbf-xpon {
        prefix bbf-xpon;
    }
    
    import bbf-xpon-onu-authentication-features {
        prefix bbf-xpon-onu-authf;
    }

    organization "Nokia";
    contact "isam.yang@nokia.com";

    description
    "This specification is published by Nokia under Non-Disclosure
    Agreement(s) (NDA) with specific parties and has to be considered
    as Confidential Information as defined in such NDA. Nokia reserves
    the right to revise this document for any reason, including but
    not limited to conformity with standards promulgated by various
    agencies, utilization of advances in the state of the technical
    areas, or the reflection of changes in the design of any
    equipment, techniques, or procedures described or referred to
    herein.

    The product specifications and other technical or performance
    information contained herein are subject to change without notice.
    Updates of this document will be issued under the above NDA's.

    Nokia makes no representation or warranty, expressed or implied,
    with respect to the sufficiency, accuracy, or utility of any
    information or opinion contained herein. Nokia expressly advises
    that any use of for any purpose or reliance upon this technical
    reference is at the risk of the user and that Nokia shall not be
    liable for any damage or injury incurred by any person arising out
    of the sufficiency, accuracy, or utility of any information or
    opinion contained herein.

    This document is not to be construed as a suggestion to any
    manufacturer to modify or change any of its products, nor does
    this document represent any commitment by Nokia to sell or
    purchase any product. Nothing contained herein shall be construed
    as conferring by implication, estoppel, or otherwise any license
    or right under any patent, whether or not the use of any
    information herein necessarily employs an invention of any
    existing or later issued patent.

    Nokia reserves the right not to offer any or all of these products
    and to withdraw any or all of them at any future time.

    Copyright (C) 2022, Nokia. All Rights Reserved";

    revision 2024-12-18 {
      description
        "add a new leaf loid-alternate-fetch-fall-back in channel-partition.";
      reference
        "TBD";
    }

    revision 2023-08-04 {
      description
        "rename feature to bbf-xpon-onu-authf:can-retrieve-loid-pre-auth.";
      reference
        "TBD";
    }
    
    revision 2023-01-11 {
      description
        "add a new leaf early-fetch-onu-loid-info in channel-partition.";
      reference
        "TBD";
    }

    augment "/if:interfaces/if:interface/bbf-xpon:channel-partition" {
      description
        "This augment controls whether the OLT fetches or not 
         the LOID info from the ONU during ONU authentication.";
      leaf early-fetch-onu-loid-info {
        if-feature "bbf-xpon-onu-authf:can-retrieve-loid-pre-auth";
        type boolean;
        default "false";
        description
          "When this leaf is false, the OLT will not fetch LOID info 
           during ONU authentication. When this leaf is true, the OLT 
           may fetch LOID info during ONU authentication if it needs 
           it to help management plane authenticate the ONU.
           The LOID info is defined in ITU-T G.988 session 9.1.1:
           1. Logical ONU ID (Logical ONU ID attribute in ME ONU-G)
           2. Logical password (Logical password attribute in ME ONU-G)";
       }
      leaf loid-alternate-fetch-fall-back {
        if-feature "bbf-xpon-onu-authf:can-retrieve-loid-pre-auth";
        type boolean;
        default "false";
        description
          "This data node is relevant only when the OLT needs to
           fetch the LOID from an ONU.
           If 'true', the OLT first uses standard G.988 Clause 9.1.1
           ONU-G ME to get ONU loid id. If the ONU doesn't respond
           or responds with NOK, OLT will use CTC-loid ME to fetch
           it again.
           If 'false', the OLT only uses standard G.988 Clause 9.1.1
           ONU-G ME to get ONU loid id.";
       }
    }
}
