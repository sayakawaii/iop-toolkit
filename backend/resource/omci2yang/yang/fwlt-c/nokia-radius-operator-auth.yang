module nokia-radius-operator-auth {
  yang-version 1.1;
  namespace "http://www.nokia.com/Fixed-Networks/BBA/yang/"
          + "nokia-radius-operator-auth";

  prefix nokia-radius-oper-auth;

  import ietf-system {
    prefix sys;
  }

  import nokia-radius-types {
    prefix nokia-radius-types;
  }

  import nokia-yang-types {
    prefix "nok-typ";
  }

  organization
    "Nokia";

  contact
    "Comments or questions about this Nokia YANG module should be
     directed to <mailto:isam.yang@nokia.com>.";

  description
    "This module contains new nodes according to Nokia specific
     requirements for Radius operator authentication.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not  to offer any or all of these
     products and to withdraw any or all of them at any future time.

     Copyright (C) 2023, Nokia. All Rights Reserved.";

  revision 2023-03-06 {
    description
      "Initial version";
    reference
      "";
  }

  feature radius-operator-auth {
    description
      "Indicates that the device supports RADIUS operator
       authentication.";
    reference
      "RFC 2865: Remote Authentication Dial In User Service (RADIUS)";
  }

  augment "/sys:system/sys:radius" {
    description
      "Augment configuration of the RADIUS client.";

    container operator-auth {
      if-feature radius-operator-auth;

      description
        "RADIUS operator authentication.";

      list policy {
        key name;
        ordered-by user;
        description
          "Configure operator RADIUS policy.";

        leaf name {
          type nok-typ:nokia-string-ascii64-or-empty;
          description
            "Name of the RADIUS policy.";
        }

        uses nokia-radius-types:nas-config;

        uses nokia-radius-types:auth-server;

        uses nokia-radius-types:acct-server;
      }

      leaf cli-session-policy {
        type leafref {
          path "../policy/name";
        }
        description
          "Operator authentication policy reference";
      }

      /* Future : a new leaf referring the policy required for 
         Netconf operator authentication*/
    }
  }
}
