module nokia-ethernet-interface-fec-mounted {
 namespace "http://www.nokia.com/Fixed-Networks/BBA/yang/nokia-ethernet-interface-fec-mounted";

 prefix "nokia-eth-intf-fec-mounted";

 import ethernet-mounted {
    prefix eth-mounted;
  }

  import ietf-interfaces-mounted {
    prefix if-mounted;
  }

  import nokia-ethernet-interface-external-speed-mounted {
    prefix nokia-eth-intf-ext-speed-mounted;
  }

  import bbf-fiber-onu-emulated-mount {
     prefix onu;
  }

  organization
    "Nokia";

  contact
    "Comments or questions about this Nokia YANG module should be
     directed to <mailto:isam.yang@nokia.com>.";

  description
    "This module contains a collection of YANG definitions for
    supporting Nokia specific requirements as applicable to its
    access network equipment.

    Specifically, this module augments the interface model with data
    that supports to configure/status of forward error correction(FEC)
    in ethernet interface.

    This specification is published by Nokia under Non-Disclosure
    Agreement(s) (NDA) with specific parties and has to be considered
    as Confidential Information as defined in such NDA. Nokia
    reserves the right to revise this document for any reason,
    including but not limited to conformity with standards
    promulgated by various agencies, utilisation of advances in the
    state of the technical areas, or the reflection of changes in the
    design of any equipment, techniques, or procedures described or
    referred to herein.

    The product specifications and other technical or performance
    information contained herein are subject to change without
    notice. Updates of this document will be issued under the above
    NDA's.

    Nokia makes no representation or warranty, expressed or implied,
    with respect to the sufficiency, accuracy, or utility of any
    information or opinion contained herein. Nokia expressly advises
    that any use of for any purpose or reliance upon this technical
    reference is at the risk of the user and that Nokia shall not be
    liable for any damage or injury incurred by any person arising
    out of the sufficiency, accuracy, or utility of any information
    or opinion contained herein.

    This document is not to be construed as a suggestion to any
    manufacturer to modify or change any of its products, nor does
    this document represent any commitment by Nokia to sell or
    purchase any product. Nothing contained herein shall be construed
    as conferring by implication, estoppel, or otherwise any license
    or right under any patent, whether or not the use of any
    information herein necessarily employs an invention of any
    existing or later issued patent.

    Nokia reserves the right not to offer any or all of these
    products and to withdraw any or all of them at any future time.

    Copyright (C) 2021, Nokia. All Rights Reserved.";


  revision 2021-08-06 {
    description
      "Initial revision of YANG model for ethernet interface to support FEC.";
    reference
        " ";
  }

  typedef fec-value {
    type enumeration {
      enum disable {
        description
          "Disable the FEC";
      }
      enum enable {
        description 
          "Enable the FEC";
      }

      enum per-802.3 {
        description
          "Apply by default the FEC configuration that is defined by 802.3 for that specific Ethernet interface flavour";	  
	  }
    }
    description
      "Enumerates the possible values for the FEC";
 }

augment '/onu:onus/onu:onu/onu:root/if-mounted:interfaces/if-mounted:interface/eth-mounted:ethernet/eth-mounted:transmission-mode/eth-mounted:auto-negotiation/eth-mounted:auto-negotiation'
   {
   when "eth-mounted:speed = 'eth-mounted:eth-if-speed-100gb' or eth-mounted:speed = 'nokia-eth-intf-ext-speed-mounted:eth-if-speed-25gb'";
   description
        "Data nodes for enable/disable the FEC.";
   leaf fec {
     type fec-value;
     default per-802.3;
     description
       "Allows to enable or disable the FEC on ethernet interface";
   }
 }

augment '/onu:onus/onu:onu/onu:root/if-mounted:interfaces-state/if-mounted:interface/eth-mounted:Ethernet'
   {
   description
        "Data nodes of FEC Status.";
   leaf fec {
     type fec-value;
     description
        "To show the FEC status of ethernet interface";
   }
 }
}
