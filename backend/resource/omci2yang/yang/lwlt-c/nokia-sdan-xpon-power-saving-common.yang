module nokia-sdan-xpon-power-saving-common {
  yang-version 1.1;
  namespace "http://www.nokia.com/Fixed-Networks/BBA/yang/"
  + "nokia-sdan-xpon-power-saving-common";

  prefix nokia-sdan-xpon-pwr-savc;

  organization
    "Nokia";

  contact
    "Comments or questions about this Nokia YANG module should be
     directed to <mailto:isam.yang@nokia.com>.";

  description
    "This module contains a collection of YANG definitions for
     supporting Nokia specific requirements as applicable to its
     access network equipment.

     Specifically, this module defines common data to manage xPON
     power saving in the OLT, such as power saving applied to
     transceivers and transceiver links.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
     Nokia reserves the right not to offer any or all of these
     products and to withdraw any or all of them at any future time.
     Copyright (C) 2025, Nokia. All Rights Reserved.";

  revision 2025-05-30 {
    description
      "Initial version of power saving module
       defining common data to manage xPON
       power-saving on OLT";
    reference
      "Nokia specific";
  }

  /* Features */

  feature xpon-transceiver-power-saving {
    description
      "Indicates that the xPON transceiver power saving feature is
       supported.";
  }

  identity power-saving-xpon-transceiver-criteria {
    description
      "Base identity for power saving criteria supported by xPON
       transceiver.";
  }

  identity none {
    base power-saving-xpon-transceiver-criteria;
    description
      "No power saving criteria is used, i.e., power saving is
       disabled.";
  }

  identity if-no-vani-configured {
    base power-saving-xpon-transceiver-criteria;
    description
      "Power saving will take place on the xPON transceiver or
       transceiver link if no vANI is configured on a channel
       partition that is (indirectly) using the transceiver or
       transceiver link.";
  }

  identity if-no-onu-present {
    base power-saving-xpon-transceiver-criteria;
    description
      "Power saving will take place on the xPON transceiver or
       transceiver link if there is no ONU present on the channel
       termination using the transceiver or transceiver link.";
  }

  grouping power-saving-xpon-transceiver-config-data {
    description
      "Grouping of power saving config data for a xPON transceiver.";

    leaf-list xpon-transceiver-criteria {
      type identityref {
        base power-saving-xpon-transceiver-criteria;
      }
      description
        "Determines under what criteria power saving should be
         applied (or not) to xPON transceiver(s) and, by
         inheritance, to their child transceiver link(s).
         The leaf-list realizes an OR'ing of criteria
         leading the transceiver(s) and their transceiver link(s)
         to be in power saving: as long as any criteria leading
         to power saving listed in the leaf-list is met, power
         saving will take place.

         The value 'none' does not lead by itself to power saving:
           - if no other value than 'none' is configured in the
             leaf-list, the transceiver and its child transceiver
             link(s) will not be in power saving. It is equivalent
             to not configuring the leaf-list at all.
           - if the leaf-list contains the value 'none' together
             with other values leading to power saving, then the
             value 'none' will be ignored as a consequence of
             logical OR'ing of powers saving criteria.

         More specifically,
           - value 'if-no-vani-configured', means that the
             transceiver-link laser transmitters feeding channel
             terminations on which no vANI is (indirectly)
             configured will be switched-off, possibly modulated
             by an optional cyclic wake-up mechanism.
           - value 'if-no-onu-present', means that the
             transceiver-link laser transmitters feeding channel
             terminations on which no ONU is present will be
             switched-off, possibly modulated by an optional
             cyclic wake-up mechanism.

         Finally, it should be noted that if the laser transmitter
         of (all) the transceiver link(s) of the transceiver are
         switched off, the whole transceiver can be switched off.";
    }

    container wake-up {
      presence
        "Parameters to control cyclic wakeup of the xPON transceiver
         laser during power saving. Cyclic wakeup of an xPON
         transceiver link laser allows the  OLT to detect ONU(s)
         that connects on the fiber attached to this transceiver
         link, even when the transceiver link is in power saving.
         When this container is not present, the laser of transceiver
         link remains OFF as long as the transceiver link is in a
         power saving.";
      description
        "The means to explicit control cyclic wakeup of the xPON
         transceiver when in power saving.";
      choice wake-up-realization {
        description
          "Provides alternative ways to realize wake-up.";
        case cyclic-wake-up {
          leaf xpon-transceiver-link-sleep-time {
            type uint32;
            units miliseconds;
            description
              "How long the transceiver link laser must remian OFF, while
               in power saving, before waking up.";
          }
          leaf xpon-transceiver-link-awake-time {
            type uint32;
            units miliseconds;
            description
              "How long the transceiver link laser must remain on
               when awake, while in power saving.";
          }
        }
      }
    }
  }
}
