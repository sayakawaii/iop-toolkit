module nokia-mgmd-ipspoof {
  yang-version 1.1;
  namespace "http://www.nokia.com/Fixed-Networks/BBA/yang/"
          + "nokia-mgmd-ipspoof";

  prefix nokia-mgmd-ipspoof;

  import ietf-interfaces {
    prefix if;
  }

  import bbf-if-type {
    prefix bbfift;
  }
             
  import bbf-mgmd {
    prefix bbf-mgmd;
  }
 
  organization
    "Nokia";

  contact
    "Comments or questions about this Nokia YANG module should be 
     directed to <mailto:isam.yang@nokia.com>."; 

  description
    "This module contains a collection of YANG definitions for 
     supporting Nokia specific requirements as applicable to its 
     access network equipment.
     
     Specifically, this module augments the mgmd model with data on 
     in case MGMD membership reports have to be checked for the 
     validity of the incoming source ip address via 
     Anti IP Spoofing.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017, Nokia. All Rights Reserved.";

  revision 2016-06-22 {
    description
      "Initial revision.
       * Approval Date:    see revision date above.
       * Publication Date: yyyy-mm-dd.";
    reference
      "TR-383: Common YANG Modules
               <https://www.broadband-forum.org/technical/download/
                        TR-383.pdf>";
  }

  augment '/bbf-mgmd:multicast/bbf-mgmd:mgmd/bbf-mgmd:multicast-vpn'
        + '/bbf-mgmd:multicast-interface-to-host' {

    description 
      "Augments new leafs to support Anti IP Spoofing checks 
       for an multicast VSI";

      leaf vlan-sub-interface-ref-for-ipspoof {
        type if:interface-ref;
        must
          "derived-from-or-self(/if:interfaces/if:interface
           [if:name = current()]/if:type,
           'bbfift:vlan-sub-interface')" {
            description 
              "The interface must be of the type 
               'vlan-sub-interface'.";
          }		  
        description
          "This object specifies the VLAN sub-interface to be used for
           performing the Anti Ip Spoofing checks for the packets which  
           are classified to an Multicast VSI.";
      }
  }  
}
