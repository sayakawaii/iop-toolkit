module nokia-bbf-xponvani-common-si {

  namespace "http://www.nokia.com/Fixed-Networks/BBA/yang/"
    + "nokia-bbf-xponvani-common-si";

  prefix nokia-bbf-xponvani-common-si;

  import nokia-sdan-service-impact {
    prefix nokia-si;
  }

  import ietf-interfaces {
    prefix if;
  }

  import bbf-xponvani{
    prefix bbf-xponvani;
  }

  organization
    "Nokia";

  contact
    "isam.yang@nokia.com";

  description
    "The NOKIA IETF/System YANG module supporting
     deviations on top of standard.";

  revision 2023-01-26 {
    description
      "Update description.";
    reference
      "Nokia Specific.";
  }
  
  revision 2023-01-03 {
    description
      "Remove upstream-fec.";
    reference
      "Nokia Specific.";
  }

  revision 2022-11-20 {
    description
      "Initial revision.";
    reference
      "Nokia Specific.";
  }

  deviation "/if:interfaces/if:interface/bbf-xponvani:v-ani/bbf-xponvani:expected-serial-number" {
      description
       "When expected-serial-number is modified, the interface will be operational down for a short time period.  
        As a consequence the connected and operational onu under this v-ani will re-range.  
        This will result in service interruptions of several seconds.";
      deviate add {
        nokia-si:service-impact;
      }
  }

  deviation "/if:interfaces/if:interface/bbf-xponvani:v-ani/bbf-xponvani:expected-registration-id" {
      description
       "When expected-registration-id is modified, the interface will be operational down for a short time period.  
        As a consequence the connected and operational onu under this v-ani will re-range.  
        This will result in service interruptions of several seconds.";
      deviate add {
        nokia-si:service-impact;
      }
  }
}
