module nokia-logging-app {

  namespace
     "http://www.nokia.com/Fixed-Networks/BBA/yang/nokia-logging-app";

  prefix log-app;

  organization
    "Nokia";

  contact
    "Comments or questions about this Nokia YANG module should be
     directed to <mailto:isam.yang@nokia.com>.";

  description
    "This module contains a collection of YANG definitions for
     supporting Nokia specific requirements as applicable to its
     access network equipment.

     Specifically, this module identifies data that potentially
     contains private data. Note that this classification is product
     independent while the support of this data is product dependent.
     I.e. it might be that data that is identified as private is not
     supported in a particular product variant.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2018, Nokia. All Rights Reserved.";

/* revision */

  revision 2023-04-21 {
    description
    "YANG error fixes";
    reference
    "Nokia specific";
  }


  revision 2022-12-20 {
    description
      "Additions in descriptions";
    reference
	"Nokia Specific.";
  }

  revision 2018-11-30 {
    description
      "Change of copyrights.";
    reference
	"Nokia Specific.";
  }

  typedef severity {
    type enumeration {
		enum "none" {
           value -2;
           description
             "This enum describes the case where no severities
              are selected.";
        }
		enum "critical" {
			value 2;
			description	"The severity level 'Critical' indicate a
			critical condition.";
		}
		enum "error" {
			value 3;
			description "The severity level 'Error'
			indicate an error condition.";
		}
		enum "warning" {
			value 4;
			description	"The severity level 'Warning'
			indicate a warning condition.";
		}
		enum "info" {
			value 6;
			description "The severity level 'Info' indicate
			an informational message.";
		}
		enum "debug" {
			value 7;
			description "The severity level 'Debug' indicating
			a debug-level message.";
		}
	}
   description
     "Supported logging levels (Severity) as defined in RFC 5424.";
 }


/************************************************************/
/*   NOKIA internal yang model for the enabling/disabling   */
/*   logging functionality on application level             */
/************************************************************/
    container applications {
                description
                  "Parameters for log levels for applications for techsupport usage.";
		list enable-logging-for{
			key "app-name";
			description
			"Configures the log level of internal loggers per application.";
			leaf app-name {
				type string;
				description
				"This leaf provide the application name (sw module ).";
			}
			list modules {
				key "mod-name";
				leaf mod-name {
					type string;
					description
					"This leaf represent an internal logger";
				}
				leaf level {
					type severity;
					mandatory true;
					description
					"This leaf specifies the syslog message severity.";
				}
				description "Logging Modules list.";
			}
		}
		list active-applications{
			key "app-name";
			config false;
			leaf app-name {
				type string;
				description
				"Provide the available for logging applications.";
			}
			list modules {
				key "mod-name";
				leaf mod-name{
					type string;
					description
					"This leaf represents an internal logger.";
				}
				leaf level {
					type severity;
					mandatory true;
					description
					"This leaf specifies the syslog message severity.";
				}
				description "Provides the severity of available internal loggers for an application.";
			}
			description "Provides the severity of available internal loggers per application.";
		}
	}
	container loggers{
                description
                  "Parameters for log levels for applications for operator usage.";
		list active-applications{
			key "app-name";
			config false;
			leaf app-name {
				type string;
				description
				"Provide the available for operator logging applications.";
			}
			list modules {
				key "mod-name";
				leaf mod-name{
					type string;
					description
					"This leaf represent operator loggers name";
				}
				leaf level {
					type severity;
					mandatory true;
					description
					"This leaf specifies the syslog message severity.";
				}
				description "Provides the severity of available operator loggers for an application";
			}
			description "Provides the severity of available operator loggers per application";
		}
		list enable-logging-for{
			key "app-name";
			description
			"enable/disable the log level per application.";
			leaf app-name {
				type string;
				description
				"This leaf provide the application name (sw module ).";
			}
			list modules {
				key "mod-name";
				leaf mod-name {
					type string;
					description
					"This leaf represent the operator loggers name";
				}
				leaf level {
					type severity;
					mandatory true;
					description
					"This leaf specifies the syslog message severity.";
				}
				description "A list containing all operator loggers for each application.";
			}
		}
	}
}
