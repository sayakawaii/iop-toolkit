module nokia-sdan-xpon-onu-state-aug {
    yang-version 1.1;
    namespace "http://www.nokia.com/Fixed-Networks/BBA/yang/" +
     "nokia-sdan-xpon-onu-state-aug";

    prefix nokia-sdan-xpon-onu-state-aug;

    import ietf-interfaces {
        prefix if;
    }

    import bbf-xpon {
        prefix bbf-xpon;
    }

    import bbf-xpon-onu-state {
        prefix bbf-xpon-onu-s;
    }

    import nokia-sdan-xpon-onu-types {
        prefix nokia-sdan-xpon-onu-types;
    }

    organization
        "Nokia";

    contact
        "isam.yang@nokia.com";

    description
    "This specification is published by Nokia under Non-Disclosure
    Agreement(s) (NDA) with specific parties and has to be considered
    as Confidential Information as defined in such NDA.  Nokia
    reserves the right to revise this document for any reason,
    including but not limited to conformity with standards promulgated
    by various agencies, utilization of advances in the state of the
    technical areas, or the reflection of changes in the design of any
    equipment, techniques, or procedures described or referred to
    herein.

    The product specifications and other technical or performance
    information contained herein are subject to change without notice.
    Updates of this document will be issued under the above NDA's.

    Nokia makes no representation or warranty, expressed or implied,
    with respect to the sufficiency, accuracy, or utility of any
    information or opinion contained herein. Nokia expressly advises
    that any use of for any purpose or reliance upon this technical
    reference is at the risk of the user and that Nokia shall not be
    liable for any damage or injury incurred by any person arising out
    of the sufficiency, accuracy, or utility of any information or
    opinion contained herein.

    This document is not to be construed as a suggestion to any
    manufacturer to modify or change any of its products, nor does
    this document represent any commitment by Nokia to sell or
    purchase any product. Nothing contained herein shall be construed
    as conferring by implication, estoppel, or otherwise any license
    or right under any patent, whether or not the use of any
    information herein necessarily employs an invention of any
    existing or later issued patent.

    Nokia reserves the right not to offer any or all of these products
    and to withdraw any or all of them at any future time.

    Copyright (C) 2022, Nokia. All Rights Reserved";

    revision 2022-01-13 {
        description
            "Initial revision.";
        reference
            "TBD";
    }

    grouping onu-data {
        description
        "detected upstream rate and fiber distance for an ONU";

        leaf detected-upstream-rate {
            type identityref {
                base nokia-sdan-xpon-onu-types:detected-upstream-rate-base;
            }

            description
                "The upstream detected rate of the ONU. While this
                value makes sense for ONUs connected to any channel
                termination, it is especially useful in case the
                channel termination is of type XGS-PON and is hosting
                dual-rate ONUs."; reference "ITU-T G.9807.1 clause
                A.9.5";
        }
    }

    augment '/if:interfaces-state/if:interface' +
       '/bbf-xpon:channel-termination' +
       '/bbf-xpon-onu-s:onu-presence-state-change' {
        description "augment onu presence state change";
        uses onu-data;
        leaf fiber-distance {
            type uint16;
            units "meters";
            description
                "This represents an estimation of the actual PON fibre
                distance from the OLT to a this ONU."; reference
                "ITU-T G.984.3 clause 10.3.6 ITU-T G.987.3 clause
                13.1.8 ITU-T G.9807.1 clause C.13.1.8 ITU-T G.989.3
                clause 13.1.8";
        }
    }


    augment '/if:interfaces-state/if:interface' +
    '/bbf-xpon:channel-termination' +
    '/bbf-xpon-onu-s:onus-present-on-local-channel-termination' +
    '/bbf-xpon-onu-s:onu' {
        description "augment onus present on local channel termination";
        uses onu-data;
    }
}
