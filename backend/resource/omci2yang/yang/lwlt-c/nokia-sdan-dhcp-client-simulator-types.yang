module nokia-sdan-dhcp-client-simulator-types {
  yang-version 1.1;
  namespace "http://www.nokia.com/Fixed-Networks/BBA/yang/"
          + "nokia-sdan-dhcp-client-simulator-types";

  prefix dhcp-client-sim-types;

  import ietf-inet-types {
    prefix inet;
  }

  import nokia-sdan-client-simulator-types {
    prefix client-simulator-types;
  }

  organization
    "Nokia";

  contact
    "Comments or questions about this Nokia YANG module should be
     directed to <mailto:isam.yang@nokia.com>.";

  description
    "This module contains new nodes according to Nokia specific
     requirements for DHCP Client session simulation types.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.


     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not  to offer any or all of these
     products and to withdraw any or all of them at any future time.

     Copyright (C) 2022, Nokia. All Rights Reserved.";

  revision 2022-09-21 {
    description
      "Initial version";
    reference
      "";
  }

  grouping session-status-params {
    description
      "State data for the simulated DHCP Client session.";

    uses client-simulator-types:simulation-session-status;
    uses client-simulator-types:simulation-status-params;

    leaf server-ip {
      type inet:ip-address;
      description
        "IP address of the Server.";
    }

    leaf xid {
      type uint32;
      description
        "Transaction ID, a random number chosen by the client,
        used by the client and server to associate messages and
        responses between a client and a server.";
      reference
        "RFC 2131 section 2 .";
    }

    leaf lease-time {
      type uint32;
      units seconds;
      description
        "The lease time offered by the DHCP Server for the IP
        address assigned to the Client.";
      reference
        "RFC 2132 section 9.2 (IP Address Lease Time).";
    }

    uses client-simulator-types:simulation-timing-params;
  }
}
