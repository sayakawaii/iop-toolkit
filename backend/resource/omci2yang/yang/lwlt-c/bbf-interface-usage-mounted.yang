module bbf-interface-usage-mounted {
  yang-version 1.1;
  namespace "urn:bbf:yang:bbf-interface-usage-mounted";
  prefix bbf-if-usg-mounted;

  import ietf-interfaces-mounted {
    prefix if-mounted;
  }

  import iana-if-type-mounted {
    prefix ianaift-mounted;
  }

  import bbf-if-type-mounted {
    prefix bbfift-mounted;
  }

  import bbf-fiber-onu-emulated-mount {
     prefix onu;
  }
  
  organization
    "Broadband Forum <https://www.broadband-forum.org>
     Common YANG Work Area";

  contact
    "Comments or questions about this Broadband Forum YANG module
     should be directed to <mailto:help@broadband-forum.org>.

     Editor:      Nick Hancock, ADTRAN

     Editor:      Ludwig Pauwels, Nokia

     PS Leader:   Joey Boyd, ADTRAN

     PS Leader:   Sowrirajan Padmanabhan, Nokia

     WA Director: Joey Boyd, ADTRAN

     WA Director: Sven Ooghe, Nokia";

  description
    "This module contains a collection of YANG definitions for
     supporting the Broadband Forum requirements on interface
     management as applicable to access network equipment. As such,
     this module is specific to access network equipment (e.g.,
     BBF-specified Access Nodes and FTTdp DPUs).

     Specifically, this module contains a collection of YANG
     definitions defining how interfaces are used.

     Copyright (c) 2017-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a3; see
     the TR itself for full legal notices.";

  revision 2018-12-03 {
    description
      "Amendment 2.
       * Approval Date:    2018-12-03.
       * Publication Date: 2018-12-03.";
    reference
      "TR-383a2: Common YANG Modules
               <https://www.broadband-forum.org/technical/download/
                        TR-383_Amendment-2.pdf>";
  }
  revision 2017-05-08 {
    description
      "Initial revision.
       * Approval Date:    see revision date above.
       * Publication Date: 2017-06-02.";
    reference
      "TR-383: Common YANG Modules
               <https://www.broadband-forum.org/technical/download/
                        TR-383.pdf>";
  }

  typedef interface-usage {
    type enumeration {
      enum user-port {
        description
          "The interface having this interface usage connects the
           Access Node to a user.";
      }
      enum network-port {
        description
          "The interface having this interface usage connects the
           Access Node to a network.";
      }
      enum subtended-node-port {
        description
          "The interface having this interface usage connects the
           Access Node to a another Access Node.";
      }
      enum inherit {
        description
          "The interface usage is not defined for this interface.
           Instead the interface usage is inherited from the interface
           usage of the lower-layer interface. If no interface-usage
           is specified at the lowest level of an interface stack,
           then the default is product and interface specific.";
      }
    }
    description
      "This type identifies the position of the interface in the
       network. Access Nodes are typically asymetric: some interfaces
       connect users to the Access Node while other interfaces connect
       the Access Node to the network.

       For some functionality of the Access Node the position of the
       interface matters.";
  }

  augment '/onu:onus/onu:onu/onu:root/if-mounted:interfaces/if-mounted:interface' {
    when
      "derived-from-or-self(if-mounted:type, 'ianaift-mounted:ethernetCsmacd') or
       derived-from-or-self(if-mounted:type, 'ianaift-mounted:ieee8023adLag') or
       derived-from-or-self(if-mounted:type, 'ianaift-mounted:ptm') or
       derived-from-or-self(if-mounted:type, 'bbfift-mounted:vlan-sub-interface') or
       derived-from(if-mounted:type, 'bbfift-mounted:ethernet-like')" {
      description
        "The interfaces applicable for interface usage data.";
    }
    description
      "Augments interfaces with nodes relative to interface usage.";

    container interface-usage {
      description
        "Provides the interface with an interface usage.";

      leaf interface-usage {
        type interface-usage;
        description
          "Identifies the position of the interface in the network.";
      }
    }
  }
}
