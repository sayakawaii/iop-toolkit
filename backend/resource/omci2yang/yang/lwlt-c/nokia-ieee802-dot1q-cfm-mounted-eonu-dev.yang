module nokia-ieee802-dot1q-cfm-mounted-eonu-dev {
  namespace
    "http://www.nokia.com/Fixed-Networks/BBA/yang/nokia-ieee802-dot1q-cfm-mounted-eonu-dev";

  prefix nokia-ieee802-dot1q-cfm-mounted-eonu-dev;

  import bbf-fiber-onu-emulated-mount {
    prefix onu;
  }

  import ieee802-dot1q-cfm-mounted {
    prefix dot1q-cfm-mounted;
  }

  organization
    "Nokia";
    
  contact
    "Comments or questions about this Nokia YANG module should be
     directed to <mailto:isam.yang@nokia.com>.";
     
  description
    "This module contains a collection of YANG deviations on top
     of standard for supporting ieee802-dot1q-cfm.yang YANG module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.lic-appsufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2017-2018, Nokia. All Rights Reserved.";

  /* revision */
  revision 2022-11-16 {
    description
      "Initial versions";
    reference
      "Nokia specific";
  }

  deviation "/onu:onus/onu:onu/onu:root/dot1q-cfm-mounted:cfm/dot1q-cfm-mounted:maintenance-domain/dot1q-cfm-mounted:fault-alarm-transmission" {
    deviate not-supported;
  }

  deviation "/onu:onus/onu:onu/onu:root/dot1q-cfm-mounted:cfm/dot1q-cfm-mounted:maintenance-domain/dot1q-cfm-mounted:maintenance-association/dot1q-cfm-mounted:fault-alarm-transmission" {
    deviate not-supported;
  }

  deviation "/onu:onus/onu:onu/onu:root/dot1q-cfm-mounted:cfm/dot1q-cfm-mounted:maintenance-group/dot1q-cfm-mounted:mep" {
      deviate add {
          max-elements 1;
      }
  }

  deviation "/onu:onus/onu:onu/onu:root/dot1q-cfm-mounted:cfm/dot1q-cfm-mounted:maintenance-group/dot1q-cfm-mounted:mep/dot1q-cfm-mounted:mac-address" {
    deviate not-supported;
  }

  deviation "/onu:onus/onu:onu/onu:root/dot1q-cfm-mounted:cfm/dot1q-cfm-mounted:maintenance-group/dot1q-cfm-mounted:mep/dot1q-cfm-mounted:inactive-remote-mep" {
    deviate not-supported;
  }

  deviation "/onu:onus/onu:onu/onu:root/dot1q-cfm-mounted:cfm/dot1q-cfm-mounted:maintenance-group/dot1q-cfm-mounted:mep/dot1q-cfm-mounted:mep-db" {
    deviate not-supported;
  }

  deviation "/onu:onus/onu:onu/onu:root/dot1q-cfm-mounted:cfm/dot1q-cfm-mounted:maintenance-group/dot1q-cfm-mounted:mep/dot1q-cfm-mounted:continuity-check/dot1q-cfm-mounted:fng-state" {
    deviate not-supported;
  }

  deviation "/onu:onus/onu:onu/onu:root/dot1q-cfm-mounted:cfm/dot1q-cfm-mounted:maintenance-group/dot1q-cfm-mounted:mep/dot1q-cfm-mounted:continuity-check/dot1q-cfm-mounted:fault-alarm-transmission" {
    deviate not-supported;
  }

  deviation "/onu:onus/onu:onu/onu:root/dot1q-cfm-mounted:cfm/dot1q-cfm-mounted:maintenance-group/dot1q-cfm-mounted:mep/dot1q-cfm-mounted:continuity-check/dot1q-cfm-mounted:highest-priority-defect" {
    deviate not-supported;
  }

  deviation "/onu:onus/onu:onu/onu:root/dot1q-cfm-mounted:cfm/dot1q-cfm-mounted:maintenance-group/dot1q-cfm-mounted:mep/dot1q-cfm-mounted:continuity-check/dot1q-cfm-mounted:defects" {
    deviate not-supported;
  }

  deviation "/onu:onus/onu:onu/onu:root/dot1q-cfm-mounted:cfm/dot1q-cfm-mounted:maintenance-group/dot1q-cfm-mounted:mep/dot1q-cfm-mounted:continuity-check/dot1q-cfm-mounted:error-ccm-last-failure" {
    deviate not-supported;
  }

  deviation "/onu:onus/onu:onu/onu:root/dot1q-cfm-mounted:cfm/dot1q-cfm-mounted:maintenance-group/dot1q-cfm-mounted:mep/dot1q-cfm-mounted:continuity-check/dot1q-cfm-mounted:xcon-ccm-last-failure" {
    deviate not-supported;
  }

  deviation "/onu:onus/onu:onu/onu:root/dot1q-cfm-mounted:cfm/dot1q-cfm-mounted:maintenance-group/dot1q-cfm-mounted:mep/dot1q-cfm-mounted:stats" {
    deviate not-supported;
  }

  deviation "/onu:onus/onu:onu/onu:root/dot1q-cfm-mounted:cfm/dot1q-cfm-mounted:maintenance-group/dot1q-cfm-mounted:mep/dot1q-cfm-mounted:transmit-loopback" {
    deviate not-supported;
  }

  deviation "/onu:onus/onu:onu/onu:root/dot1q-cfm-mounted:cfm/dot1q-cfm-mounted:maintenance-group/dot1q-cfm-mounted:mep/dot1q-cfm-mounted:transmit-linktrace" {
    deviate not-supported;
  }

  deviation "/onu:onus/onu:onu/onu:root/dot1q-cfm-mounted:cfm/dot1q-cfm-mounted:maintenance-group/dot1q-cfm-mounted:mep/dot1q-cfm-mounted:linktrace-reply" {
    deviate not-supported;
  }
}
