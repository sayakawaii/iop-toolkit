module nokia-l2-forwarding-forwarding-database-reset {
  yang-version 1.1;
  namespace "http://www.nokia.com/Fixed-Networks/BBA/yang/"
          + "nokia-l2-forwarding-forwarding-database-reset";
  prefix nokia-l2-fwd-rst;

  import bbf-l2-forwarding {
    prefix bbf-l2-fwd;
  }

  import bbf-l2-forwarding-shared-fdb {
    prefix bbf-l2-sfdb;
  }

  import ietf-netconf-acm {
    prefix nacm;
  }

  import ietf-interfaces {
      prefix if;
  }

  import bbf-xpon-if-type {
      prefix bbf-xponift;
  }
  
  organization
    "Nokia";

  contact
    "Comments or questions about this Nokia YANG module should be 
     directed to <mailto:isam.yang@nokia.com>.";

  description
    "This module contains a collection of YANG definitions for 
     supporting Nokia specific requirements as applicable to its 
     access network equipment.
     
     Specifically this module contains a collection of YANG 
     definitions for actions to be executed on forwarding databases.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017, Nokia. All Rights Reserved.";

  revision 2025-06-22 {
    description
      "Augmented new leaf 'remove-mac-addresses-at-remote-uni-down' to
       interface Xpath for olt-v-enet type.";
    reference
      "Nokia specific";
  }

  revision 2023-10-26 {
    description
      "corrected the remove-mac-addresses-from-port-down leaf description,
        From - value 'true' of the leave
        To - value 'true' of the leaf";
    reference
      "Nokia specific";
  }

  revision 2019-02-18 {
    description
      "Removed following actions,
       /forwarding-state/forwarding-databases/forwarding-database/reset-forwarding-database
       /forwarding-state/forwarding-databases/forwarding-database/reset-interface-in-forwarding-database
       /forwarding-state/forwarding-databases/forwarding-database/remove-mac-address-from-forwarding-database";
    reference
      "Nokia specific";
  }

  revision 2018-09-07 {
    description
      "Added nacm:default-deny-all extenstion for following actions,
       /forwarding-state/forwarding-databases/reset-forwarding-databases,
       /forwarding-state/forwarding-databases/reset-interface,
       /forwarding-state/forwarding-databases/forwarding-database/reset-forwarding-database
       /forwarding-state/forwarding-databases/forwarding-database/reset-port-in-forwarding-database
       /forwarding-state/forwarding-databases/forwarding-database/reset-interface-in-forwarding-database
       /forwarding-state/forwarding-databases/forwarding-database/remove-mac-address-from-forwarding-database";
    reference
      "Nokia specific";
  }

  revision 2018-05-08 {
    description
      "Initial revision.
       * Approval Date:    see revision date above.
       * Publication Date: yyyy-mm-dd.";
    reference
      "Nokia specific";
  }

  augment '/bbf-l2-fwd:forwarding/bbf-l2-fwd:forwarding-databases' {
    description
      "Augment the forwarder forwarding databases with actions.";

    leaf remove-mac-addresses-from-port-down {
      type boolean;
      default "false";
      description
        "For independent forwarding databases:
         At the occasion the operational state of the interface 
         referenced by a forwarder port is different from 'up', or in 
         case the operational state of a lower layer interface of the 
         interface referenced by a forwarder port is different from 
         up, then the value 'true' of the leaf instructs the system
         to remove the MAC addresses that were learned for the 
         forwarder port from the forwarding database.
         
         For shared forwarding databases:
         At the occasion the operational state of the interface 
         referenced by a forwarder is different from 'up', or in case 
         the operational state of a lower layer interface of the 
         interface referenced by a forwarder is different from  up, 
         then the value 'true' of the leaf instructs the system to
         remove the MAC addresses that were learned for the interface
         from the forwarding database.";
    }    
  }
  
  augment '/bbf-l2-fwd:forwarding-state'
        + '/bbf-l2-fwd:forwarding-databases' {
    description
      "Augment the forwarder forwarding databases with actions.";

    action reset-forwarding-databases {
      nacm:default-deny-all;
      description
        "When the action is received, all the forwarding databases 
         will reset. This means that all dynamically learned MAC 
         addresses will be removed from all the forwarding 
         databases.";
    }
    
    action reset-interface {
      nacm:default-deny-all;
      description
        "For independent forwarding databases:
         When the action is received, the system will search in all 
         forwarding databases for all MAC addresses dynamically 
         learned on a forwarder port that references the specified 
         interface, or are learned on a forwarder port for which the 
         specified interface is a lower layer interface of the 
         referenced interface and it will remove all these MAC 
         addresses from the forwarding database.
         
         For shared forwarding databases:
         When the action is received, the system will search in all 
         forwarding databases for all MAC addresses dynamically 
         learned on the specified interface, or lare earned on an 
         interface for which the specified interface is a lower layer 
         interface of the referenced interface and it will remove all 
         these MAC addresses from the forwarding database.";

      input {
        uses bbf-l2-sfdb:ethernet-interface-state;
      }
    }
  }
  
  augment '/bbf-l2-fwd:forwarding-state'
        + '/bbf-l2-fwd:forwarding-databases'
        + '/bbf-l2-fwd:forwarding-database' {
    description
      "Augment the forwarder forwarding database with actions.";

    action reset-port-in-forwarding-database {
      nacm:default-deny-all;
      description
        "When the action is received, the system will search in the 
         forwarding database for all MAC addresses dynamically learned
         on the specified forwarder port, and it will remove them from
         the forwarding database.";

      input {
        uses bbf-l2-fwd:forwarder-port-state;
      }
    }
  }

  augment '/if:interfaces/if:interface/bbf-l2-fwd:mac-learning' {
    when "derived-from-or-self(../if:type, 'bbf-xponift:olt-v-enet')"
    {
      description
        "Allow enabling interface level flush FDB only for olt-v-enet type.";
    }
    description
      "Augment remove-mac-addresses-at-remote-uni-down leaf to the interface Xpath.";

    leaf remove-mac-addresses-at-remote-uni-down
    {
      type boolean;

      description
        "The MACs are flushed on this interface when this leaf's value
         is configured as 'true' and the Oper-reason of olt-v-enet interface
         changes to 'remoteInterfaceDown'.

         It is not required that the system level leaf
         'remove-mac-addresses-from-port-down' must be enabled for
         this leaf to function.";
    }
  }

}
