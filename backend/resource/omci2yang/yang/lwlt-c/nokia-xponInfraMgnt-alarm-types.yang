module nokia-xponInfraMgnt-alarm-types {
     yang-version 1.1;
     namespace "https://www.nokia.com/Fixed-Networks/BBA/yang/nokia-xponInfraMgnt-alarm-types";
     prefix xponInfraMgnt-al;

     import nokia-base-alarm-types {
         prefix base-al;
     }

     organization
      "Nokia";

     contact
      "Comments or questions about this Nokia YANG module should be
       directed to <mailto:isam.yang@nokia.com>.";

     description
       "This module provides the details of supported xponInfraMgnt alarm types.

        This specification is published by Nokia under Non-Disclosure
        Agreement(s) (NDA) with specific parties and has to be considered
        as Confidential Information as defined in such NDA. Nokia
        reserves the right to revise this document for any reason,
        including but not limited to conformity with standards
        promulgated by various agencies, utilisation of advances in the
        state of the technical areas, or the reflection of changes in the
        design of any equipment, techniques, or procedures described or
        referred to herein.

        The product specifications and other technical or performance
        information contained herein are subject to change without
        notice. Updates of this document will be issued under the above
        NDA's.

        Nokia makes no representation or warranty, expressed or implied,
        with respect to the sufficiency, accuracy, or utility of any
        information or opinion contained herein. Nokia expressly advises
        that any use of for any purpose or reliance upon this technical
        reference is at the risk of the user and that Nokia shall not be
        liable for any damage or injury incurred by any person arising
        out of the sufficiency, accuracy, or utility of any information
        or opinion contained herein.

        This document is not to be construed as a suggestion to any
        manufacturer to modify or change any of its products, nor does
        this document represent any commitment by Nokia to sell or
        purchase any product. Nothing contained herein shall be construed
        as conferring by implication, estoppel, or otherwise any license
        or right under any patent, whether or not the use of any
        information herein necessarily employs an invention of any
        existing or later issued patent.

        Nokia reserves the right not to offer any or all of these
        products and to withdraw any or all of them at any future time.

        Copyright (C) 2018, Nokia. All Rights Reserved.";

     revision 2023-12-15 {
       description
         "Add identity 'channel-termination-data-path-integrity-failure'
          for xponInfra management alarms";
       reference
         "Nokia specific";
     }

     revision 2022-06-14 {
       description
         "xponInfra management alarms";
       reference
         "Nokia specific";
     }

     revision 2021-02-05 {
       description
         "Rename yang with nokia prefix.
           - nokia-xponInfraMgnt-alarm-types
         ";
       reference
         "Nokia specific";
     }

     revision 2020-05-29 {
      description
        "xponInfra management alarms";
      reference
        "Nokia specific";
     }

     revision 2020-04-30 {
      description
        "xponInfra management alarms";
      reference
        "Nokia specific";
     }

     revision 2018-04-23 {
      description
        "xponInfra management alarms";
      reference
        "Nokia specific";
     }


    identity xponInfraMgnt {
        base base-al:communications-alarm;
        description
            "Abstract alarm type for xponInfraMgnt alarms";
    }


// ---- draft proposal alarm identifiers for xponInfraMgnt ----

    identity channel-termination-communication-failure {
        base xponInfraMgnt;
        description
            "Channel Termination Communication Failure on OLT Port.";
    }

    identity channel-termination-transmitter-failure {
        base xponInfraMgnt;
        description
            "Transmitter failure (TF) for OLT port.";
    }

    identity channel-termination-provisioning-mismatch {
        base xponInfraMgnt;
        description
            "Channel Termination failed to be provisioned. Mismatch between Channel Termination Equipment and Channel Termination provisioning attributes.";
    }

    identity channel-termination-loss-of-signal {
        base xponInfraMgnt;
        description
            "Loss of signal (PON_LOS) detected on OLT port.";
    }

    identity channel-termination-rogue-test-ongoing {
        base xponInfraMgnt;
        description
            "A diagnostics test is currently active on the Channel Termination looking for misbehaving ONUs.";
    }

    identity channel-termination-inactive-onu-disabled {
        base xponInfraMgnt;
        description
            "This alarm indicates that due to 'rogue ONU testing',  one or more unknown ONUs on the Channel Termination may have been DISABLED via OLT broadcast.";
    }

    identity channel-termination-optics-mismatch {
        base xponInfraMgnt;
        description
            "This alarm indicates that there is mismatch between the channel-pair configuration and the actual SFP laser transceiver that is plugged in.";
    }

    identity onu-upstream-rx-power-exceed-threshold {
        base xponInfraMgnt;
        description
            "Received power of ONU at OLT PON side, on per ONU basis, is exceeding the system defined thresholds.";
    }

    identity backplane-link-speed-incompatible {
        base xponInfraMgnt;
        description
            "The backplane link speed is not compatible with the PON configuration.";
    }

    identity channel-termination-data-path-integrity-failure {
        base xponInfraMgnt;
        description
            "Data path integrity failure detected on OLT port.";
    }

}
