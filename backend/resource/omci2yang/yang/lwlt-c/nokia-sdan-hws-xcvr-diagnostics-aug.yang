module nokia-sdan-hws-xcvr-diagnostics-aug {

    yang-version 1.1;
    
    namespace "http://www.nokia.com/Fixed-Networks/BBA/yang/" +
        "nokia-sdan-hws-xcvr-diagnostics-aug";

    prefix nokia-sdan-hws-xcvr-diagnostics-aug;

    import ietf-interfaces {
        prefix if;
    }

    import ietf-hardware {
        prefix hw;
    }

    import bbf-hardware-transceivers {
        prefix bbf-hw-xcvr;
    }

    import bbf-xpon-types {
        prefix bbf-xpon-types;
    }

    organization "Nokia";
    contact "isam.yang@nokia.com";

    description
    "This specification is published by Nokia under Non-Disclosure
    Agreement(s) (NDA) with specific parties and has to be considered
    as Confidential Information as defined in such NDA. Nokia reserves
    the right to revise this document for any reason, including but
    not limited to conformity with standards promulgated by various
    agencies, utilization of advances in the state of the technical
    areas, or the reflection of changes in the design of any
    equipment, techniques, or procedures described or referred to
    herein.

    The product specifications and other technical or performance
    information contained herein are subject to change without notice.
    Updates of this document will be issued under the above NDA's.

    Nokia makes no representation or warranty, expressed or implied,
    with respect to the sufficiency, accuracy, or utility of any
    information or opinion contained herein. Nokia expressly advises
    that any use of for any purpose or reliance upon this technical
    reference is at the risk of the user and that Nokia shall not be
    liable for any damage or injury incurred by any person arising out
    of the sufficiency, accuracy, or utility of any information or
    opinion contained herein.

    This document is not to be construed as a suggestion to any
    manufacturer to modify or change any of its products, nor does
    this document represent any commitment by Nokia to sell or
    purchase any product. Nothing contained herein shall be construed
    as conferring by implication, estoppel, or otherwise any license
    or right under any patent, whether or not the use of any
    information herein necessarily employs an invention of any
    existing or later issued patent.

    Nokia reserves the right not to offer any or all of these products
    and to withdraw any or all of them at any future time.

    Copyright (C) 2022, Nokia. All Rights Reserved";

    revision 2022-10-19 {
        description
        "using definition bbf-xpon-types:onu-serial-number in BBF.";
        reference
        "TBD";
    }

    revision 2022-01-13 {
        description
        "Initial revision.";
        reference
        "TBD";
    }

    augment "/hw:hardware-state/hw:component" +
        "/bbf-hw-xcvr:transceiver-link/bbf-hw-xcvr:diagnostics" {
        description
            "Data nodes for components of identity class
            'transceiver-link'.";

        list rssi-onu {

            key "detected-serial-number";
            description
                "This list is only applicable when the
                transceiver-link is used for xPON. It contains the
                averaged power level of each ONU (whether configured
                as a vANI or non-configured) which is currently
                present on the transceiver-link.";

            leaf detected-serial-number {
                type bbf-xpon-types:onu-serial-number;
                mandatory true;
                description
                    "The serial number of the ONU. The serial number
                     is unique for each ONU.  It contains the vendor
                     ID and vendor specific serial number.

                         The first four bytes are an ASCII-encoded
                         vendor ID four letter mnemonic.

                         The second four bytes are a binary encoded
                         serial number, under the control of the ONU
                         vendor.";
                reference
                    "ITU-T G.984.3, section 9.2.4.1.";
            }

            leaf rssi {
                type int16;
                units "0.1dBm";
                config false;
                mandatory true;

                description
                    "Received Signal Strength Indication (RSSI). This
                    is a measurement at the OLT of the averaged
                    optical power received from a specific ONU
                    operating in burst mode.";

                reference
                    "ITU-T G.Sup48-20, section 3.1.";
            }

            leaf v-ani-ref {
                type if:interface-ref;
                description
                    "The v-ani interface related to this ONU when
                    configured on this OLT. This YANG leaf is not
                    present if no virtual ANI is corresponding to the
                    ONU in the OLT.";
            }
        }
    }
}
