module nokia-ipfix {
  yang-version 1.1;
  namespace "http://www.nokia.com/Fixed-Networks/BBA/yang/"
    + "nokia-ipfix";

  prefix  nokia-ipfix;

  import ietf-ipfix-psamp {
    prefix ipfix;
  }

  import iana-crypt-hash {
    prefix ianach;
  }

  import ietf-netconf-acm {
    prefix nacm;
  }

  import ietf-yang-types {
    prefix yang;
  }

  import ietf-inet-types {
    prefix inet;
  }

  import ietf-interfaces {
    prefix if;
  }

  import ietf-tls-client {
    prefix tlsc;
  }

  import iana-hardware {
    prefix ianahw;
  }

  import ietf-tcp-common {
    prefix tcpcmn;
  }

  import nokia-sdan-keystore-types {
    prefix nokia-ks;
  }

  import nokia-sdan-est-client {
    prefix estc;
  }

  organization
    "Nokia";

  contact
    "Comments or questions about this Nokia YANG module should be
     directed to <mailto:isam.yang@nokia.com>.";

  description
    "This module contains a collection of YANG definitions for
     supporting Nokia specific requirements as applicable to its
     access network equipment.

     Specifically, this module augments the ietf-ipfix-psamp model
     with additional configuration and operational data. Some
     of them specific to IPFIX tcpExporter in fallback mode.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2018, Nokia. All Rights Reserved.";

  revision 2026-08-25  {
    description "Include support for export-monitoring PM data.";
    reference "Nokia specific.";
  }

  revision 2026-04-16  {
    description "Include support for on-demand presence container with new leaf for correlation-id and action once.
                 Include new fields correlation-id and cache-config-mode fields to be added to outgoing packets.";
    reference "Nokia specific.";
  }

  revision 2025-08-25  {
    description "Add to-aggregate field to outgoing packets. Update range of heartbeat-interval";
    reference "Nokia specific.";
  }

  revision 2025-05-02  {
    description "EST keystore support.";
    reference "Nokia specific.";
  }

    revision 2025-04-26  {
    description "Add templateDataRecordsAccessTime in IPFIX's template-info operational data.";
    reference "Nokia specific.";
  }

  revision 2024-11-27  {
    description "Add hierarchy-meta-info to outgoing packets.";
    reference "Nokia specific.";
  }

  revision 2024-09-05  {
    description "Remove resource from scope-identifier and add a separate leaf-list.";
    reference "Nokia specific.";
  }

  revision 2024-06-05  {
    description "Keystore support for ipfix.";
    reference "Nokia specific.";
  }

  revision 2024-03-13 {
      description "Include total-dropped-data-records (applicable only to caches marked as conveying critical content).
                   Update interface-type by allowing both ietf-interfaces and ietf-interfaces-mounted namespaces to be configured";
      reference "Nokia specific";
  }

  revision 2023-11-22 {
      description "Include data-presence-indication.
                   Adding critical-content config leaf and operational leafs rotated-data-sets and stored-data-sets.
                   Updates collector-connection-status structures in order to send notifications for both IP and FQDN configurations";
      reference "Nokia specific";
  }

  revision 2023-08-22 {
    description "Include FQDN.";
    reference "Nokia specific.";
  }

  revision 2023-08-21 {
    description "Include TCP Keep-Alive Parameters.";
    reference "Nokia specific.";
  }

  revision 2023-05-31 {
    description "Resolve yang errors about caonical order and missing references.";
    reference "Nokia internal.";
  }

  revision 2023-05-27 {
    description "Solve yang errors add references and resolve canonical order according to RFC 6020.";
    reference "Nokia specific";
  }

  revision 2023-05-25 {
      description "Include configuration of on-change-audit-interval, on-change & action for full-sync";
      reference "Nokia specific";
  }

  revision 2023-04-03 {
      description "Include on-change specific elements - cache-sequence-number, delete-flag, record-type";
      reference "Nokia specific";
  }

  revision 2022-09-12 {
      description "Update choice 'scope' with case for hardware-class & resource";
      reference "Nokia specific";
  }

  revision 2021-12-18 {
      description "Adding last-message leaf to indicate the end of streamed data.";
      reference "Nokia specific";
  }

  revision 2021-07-22 {
      description "Adding description in all must clauses for Yang data constraints information";
      reference "Nokia internal.";
  }

  revision 2020-10-10 {
    description
      "Added choice scope-identifier";
    reference "Nokia specific";
  }

  revision 2019-12-24 {
    description
      "Added notification to report the status of the
       connection to Collector";
    reference "Nokia specific";
  }

  revision 2019-11-25 {
    description
      "Removed leaf session-persistency and session-randomisation-window";
    reference "Nokia specific";
  }

  revision 2019-09-05 {
    description
      "Added 'count' for priority to ensure that the value is unique";
    reference "Nokia specific";
  }

  revision 2019-03-12 {
    description
      "Reverted destination priority range";
    reference "Nokia specific";
  }

  revision 2019-01-10 {
    description
      "Modified destination priority range";
    reference "Nokia specific";
  }

  revision 2018-08-29 {
    description
      "Added nacm:default-deny-all extenstion for action revert.";
    reference "Nokia specific";
  }

  revision 2018-06-08 {
    description
      "Initial revision";
    reference
      "Nokia specific";
  }

  augment '/ipfix:ipfix' {
    description
      "Augments the IPFIX configuration container.";

    leaf ipfix-exporting-enable {
      type  boolean;
      default "false";
      description
        "Used to start/stop the IPFIX exporting.";
    }

    leaf randomize-data-collection {
      type boolean;
      default "false";
      description
        "Used to randomize the data collection & the subsequent export of all enabled non-PM caches.
         If set to true, the data collection & the subsequent export will be offset by a random seed over the wall-clock expiry.
         If set to false, the data collection & the subsequent export of all enabled caches will be aligned to wall-clock.";
    }

    leaf on-change-audit-interval {
      type uint32 {
        range "0..86400";
      }
      units "seconds";
      must ". mod 1800 = 0" {
        error-message "Audit interval should be in multiples of 1800sec (30min)";
        description "Audit interval can only be a multiples of 1800sec (30min)";
      }
      default 3600;
      description
        "Interval at which the on-change caches should be audited when no on-change data is exported in the interval (wall-clock aligned).
         An audit message will be exported to the collector at the end of the audit interval (after a random offset) when no on-change data is exported in the interval.
         In the audit message, only the record-type & the cache-sequence-number will be filled.
         All the other fields will be set to default/dummy values.
         This audit message can be used by the collector to validate the cache-sequence-number &
         trigger a full sync of data for the cache that is configured on-change if required.
         Value 0 can be used to disable the export of audit messages.";
    }

    leaf export-monitoring-enable {
      type boolean;
      default "false";
      description
        "This leaf enables or disables the export-monitoring performance counters.";
    }

        leaf hierarchy-meta-info {
          type string;
          config "false";
          description
            "This leaf provides information on the interface type or hardware class, along with the configured interface/hardware component metadata.
             It is used only as part of the exported data to the collector.";
        }

        leaf collection-timestamp {
          type yang:date-and-time;
          config "false";
          description
            "Timestamp to indicate the data collection time of the instance of data.
            It is used only as part of the exported data to the collector.";
        }

        leaf last-message {
          type boolean;
          config "false";
          description
            "Used to indicate the last instance of streamed data of a configured cache for an interval.
            It is used only as part of the exported data to the collector.
            The last instance will have this value as 'true'.
            All other instances will have this value as 'false'.";
        }

        leaf cache-sequence-number {
          type uint32;
          config "false";
          description
            "Sequence number per cache; applicable only for caches configured as on-change or on-demand.
            It is used only as part of the exported data to the collector.
            The sequence number will be incremented by 1 for each data-record for cache (except an audit message)
            irrespective of the connection status with the collector.
            This will be reset to 0 when an action to trigger 'full-data-sync' is used for an on-change cache,
                 when an action to trigger 'once' is used for an on-demand cache,
                 when the fields of the cache is modified or when ipfix-exporting is disabled.
                   This number will not be impacted by any change in the connection status with the collector.";
        }

        leaf record-type {
          type enumeration {
            enum full-sync {
              description
                "The data-record corresponds to a full-sync of data";
            }
            enum on-change {
              description
                "The data-record corresponds to an on-change data";
            }
            enum audit {
              description
                "The data-record corresponds to an audit.
                This will be used when there is no on-change data for one complete audit interval (wall-clock aligned) &
                when connection with collector is established.";
            }
            enum periodic {
              description
                "The data-record corresponds to a periodic export of data";
            }
          }
          config "false";
          description
            "Data record type; applicable only for caches configured as on-change.
            It is used only as part of the exported data to the collector.";
        }

        leaf delete-flag {
          type boolean;
          config "false";
          description
            "Indicates if a data-record corresponds to an instance deletion; applicable only for caches configured as on-change.
            It is used only as part of the exported data to the collector.
            Value will be true for cases where a data-instance is deleted.
            Value will be false for other cases (instance creation/modification)";
        }

        leaf data-presence-indication {
          type binary;
          config "false";
          description
            "Indicates the presence of real data for each field in the template.
            This will always be the first Information Element in every data record.
            Bit 0 corresponds to the second field, bit 1 to the third field and so on (no bit assigned for the data-presence-indication).
            Bit value 1 indicates that an actual value exists for the field & bit value 0 indicates that the value does not exist & a dummy value is added by the exporter.
            An empty value indicates that all fields have real data for the instance.
            It is used only as part of the exported data to the collector.";
        }

        leaf to-aggregate {
          type boolean;
          config "false";
          description
            "This leaf provides aggregation state info of interfaces per either LAG interface-type or VSIs created on top of LAG.
             It is used only as part of the exported data to the collector.";
        }

        leaf cache-config-mode {
          type enumeration {
            enum periodic {
              value 1;
              description
                "The cache is configured in periodic mode with an export-interval.";
            }
            enum on-change {
              value 2;
              description
                "The cache is configured in on-change with or without a heartbeat-interval.";
            }
            enum on-demand {
              value 3;
              description
                "The cache is configured in on-demand mode.";
            }
          }
          config "false";
          description
            "This value is used as part of the Options-Template-2 to indicate to the collector about the mode of configuration of each cache.
             It is used only as part of the template to the collector.";
        }

        leaf correlation-id {
          type string {
            length "0..16";
          }
          config "false";
          description
            "This leaf provides the correlation-id that was used as input to the action 'once' to trigger on-demand data export.
             It is used only as part of the exported data to the collector.";
        }
  }

  augment '/ipfix:ipfix/ipfix:cache' {
    description
      "Augments the IPFIX cache list.";

    leaf reporting-enable {
      type boolean;
      default "false";
      description
        "If present, this template will be exported in normal mode
         reporting.";
    }

    leaf critical-content {
      type boolean;
      default "false";
      description
         "Indicates that the cache's data should not be discarded when the connection is lost
          (they will remain in memory and sent to the collector when connectivity is restored)";
    }

    leaf stored-data-records {
      type uint32;
      config false;
      description
        "Indicates the number of data-records that are maintained in memory for this cache, due to the ongoing connectivity loss
         (applicable only to caches marked as conveying critical-content)";
    }

    leaf dropped-data-records {
      type uint32;
      config false;
      description
        "Indicates the number of data-records that have been dropped for this cache, due to the ongoing connectivity loss
         (applicable only to caches marked as conveying critical-content)";
    }

    leaf total-dropped-data-records {
      type uint32;
      config false;
      description
        "Indicates the total number of data-records that have been dropped for this cache, during connectivity losses
         (applicable only to caches marked as conveying critical-content)";
    }

    choice scope-identifier {
      description "Defines the scope of the data to be exported for the configured ieName(s) in the cache";
      case interface-type {
        leaf-list interface-type {
          type union {
            type identityref {
                base if:interface-type;
            }
          }
          description
          "Interface types of the data to be exported.";
        }
      }
      case hardware-class {
        leaf-list hardware-class {
          type identityref {
            base ianahw:hardware-class;
          }
          description
          "Hardware class of the data to be exported.";
        }
      }
    }

    leaf-list resource {
      type instance-identifier {
        require-instance false;
      }
      max-elements 5;
      description
      "Resources/instances of the data to be exported.";
    }

    leaf template-id {
      type uint16 {
        range "256..65535";
      }
      config false;
      description
        "This number indicates the Template ID associated with this
         Cache.";
    }

    action full-data-sync {
      nacm:default-deny-all;
      description
        "Trigger a full data sync for the cache configured as on-change.
         The full data for the cache at the time the action is invoked will be exported to the collector.
         Not applicable for periodic caches.";
    }

/*
    // To be enabled in future release
    action reset-critical-data-records-statistics {
      nacm:default-deny-all;
      description
        "Purges all currently stored data-records for caches marked as conveying critical-content,
         and resets all relevant statistics for dropped data-records";
    }
*/
  }

  augment '/ipfix:ipfix/ipfix:cache/ipfix:CacheType/ipfix:permanentCache/ipfix:permanentCache' {
   container on-change {
      presence "If on-change is present, changed data-instances will be exported to the collector when a change occurs for the instance.";
      description "on-change configuration of the cache";
      leaf heartbeat-interval {
        type uint32 {
          range "0 | 3600..86400";
        }
        units seconds;
        must ". mod 3600 = 0" {
          error-message "heartbeat interval should be in multiples of 3600 (value is in seconds)";
          description "Heartbeat interval can only be a multiple of 3600 (value is in seconds)";
        }
        default 0;
        description "This parameter configures the interval (in seconds) for periodical export of caches that will also export the data on-change.";
      }
    }
    description "on-change configuration of the cache.";
  }

  augment '/ipfix:ipfix/ipfix:cache/ipfix:CacheType/ipfix:permanentCache/ipfix:permanentCache' {
   container on-demand {
      presence "If on-demand is present, data for the cache can be exported on-demand using an action.";
      description "on-demand configuration of the cache";

      action once {
        nacm:default-deny-all;
        description
          "Trigger a data export for the cache configured as on-demand.";
        input {
          leaf correlation-id {
          type string {
            length "0..16";
          }
          description "This parameter configures correlation-id to be able to map an on-demand request to the on-demand data that is exported in response to the request. This will be part of every data-record exported for the action 'once'";
          }
        }
      }
    }
    description "on-demand configuration of the cache.";
  }


  augment '/ipfix:ipfix/ipfix:exportingProcess' {
    when "derived-from-or-self(ipfix:exportMode, 'ipfix:fallback')" {
     description
       "Only supported if the exportMode is fallback.";
    }
    description
     "Augments the IPFIX exportingProcess list.";

    leaf re-transmission-timeout {
      type uint16;
      units seconds;
      default 60;
      description
        "Maximum time before deciding to switch to another
         collector in the list.This parameter is only applicable
         for fallback mode.";
    }

    uses tcpcmn:tcp-common-grouping;

    action revert {
      nacm:default-deny-all;
      description
        "Revert the transport session to primary collector. This
         parameter is only applicable for fallback mode.";
    }
  }

  augment '/ipfix:ipfix/ipfix:exportingProcess/ipfix:destination/ipfix:DestinationParameters/ipfix:tcpExporter/ipfix:tcpExporter'
        + '/nokia-ipfix:certificate/nokia-ipfix:server-auth' {
    description "Augments CA certificate configuration with a reference to an EST CA certificate profile";
    uses estc:est-ca-certificate-profile-ref-grouping;
  }

  augment '/ipfix:ipfix/ipfix:exportingProcess/ipfix:destination/ipfix:DestinationParameters/ipfix:tcpExporter/ipfix:tcpExporter'
        + '/nokia-ipfix:certificate/nokia-ipfix:client-identity'
        + '/nokia-ipfix:auth-type/nokia-ipfix:certificate/nokia-ipfix:certificate/nokia-ipfix:local-or-keystore/nokia-ipfix:keystore' {
    description "Augments certificate configuration with a choice between central keystore reference and EST certificate profile";

    choice certificate-reference-choice {
      description "Choice between a central keystore reference and an EST certificate profile";

      case central-keystore-reference {
        container central-keystore-reference {
          uses nokia-ks:asymmetric-key-certificate-ref-grouping;
          description "A reference to a specific certificate associated with an asymmetric key stored in the central keystore.";
        }
      }
      case est-certificate-profile-reference {
        container est-certificate-profile-reference {
          uses estc:est-certificate-profile-ref-grouping;
          description "Reference to an EST certificate profile for TLS identity configuration.";
        }
      }
    }
  }

  grouping ipfix-performance-parameters {
    description
      "Defines the performance parameters for ipfix data export.";
    leaf total-attributes {
      type yang:counter64;
      description
        "This is the total number of attributes (ieNames) exported for all caches in the interval.";
    }
    leaf messages {
      type yang:counter64;
      description
        "This is the total number of ipfix messages exported in the interval.";
    }
    leaf on-change-records {
      type yang:counter64;
      description
        "This is the total number of ipfix on-change data-records exported in the interval.";
    }
    leaf bytes {
      type yang:counter64;
      description
        "This is the total number of bytes exported in the interval.";
    }
  }

  grouping performance-history-interval-parameters {
    description
      "Defines common parameters required when defining history interval performance counters.";
    leaf measured-time {
      type uint32;
      description
        "Reports the amount of time, measured in seconds, that statistics for this interval have been counted.";
    }
    leaf invalid-data-flag {
      type boolean;
      description
        "Reports the validity of the corresponding PM data.";
    }
    leaf time-stamp {
      type yang:date-and-time;
      description
        "Reports the start date/time for this interval.";
    }
  }

  typedef export-monitoring-interval {
    type uint8 {
      range "0..1";
    }
    description
      "Defines the range of export-monitoring intervals.";
  }

  augment '/ipfix:ipfix/ipfix:exportingProcess/ipfix:destination' {
    description
      "Augments the destination list within the IPFIX exportingProcess
       list.";

    leaf priority {
      type uint8 {
        range "1..255";
      }
      must "(count(../../ipfix:destination[priority = current()]) <= 1)" {
        error-message "Priority value should be unique";
        description "The priority value (range 1..255) should be unique for each destination endpoint";
      }
      description
        "Used to set priority to each collector. Value 1 means highest
         priority and 255 means lowest priority.";
    }

    container export-monitoring {
      config "false";
      description
        "Export monitoring parameters.";

      container performance {
        description
          "Performance parameters.";
        container intervals-15min {
          description
            "15 minute interval performance history.";
          leaf number-of-intervals {
            type export-monitoring-interval;
            description
              "The total number of 15-minute PM intervals for which data was collected.";
          }
          leaf non-valid-intervals {
            type export-monitoring-interval;
            description
              "The number of 15-minute PM intervals for which the data is considered to be invalid or incomplete.";
          }

          container current {
            description
              "Contains the counts that are currently accumulating.";
            uses ipfix-performance-parameters;
          }
          list history {
            key "interval-number";
            max-elements 1;
            description
              "A history of 15 minute intervals.";
            leaf interval-number {
              type uint8 {
                range "1";
              }
              description
                "The number of the interval relative to the current interval.";
            }
            uses performance-history-interval-parameters;
            uses ipfix-performance-parameters;
          }
        }
      }
    }
  }

  augment '/ipfix:ipfix/ipfix:exportingProcess/ipfix:destination/ipfix:DestinationParameters/ipfix:tcpExporter/ipfix:tcpExporter/ipfix:transportSession/ipfix:template' {
    description
      "Augments the tcpExporter destination's transportSession/template data list";

    leaf templateDataRecordsAccessTime {
      type yang:date-and-time;
      config false;
      description
        "Augments the template list under transportSession data within the destination list of
         the IPFIX exportingProcess list, with information on the last-accessed timestamp of data-records.";
    }
  }

  augment '/ipfix:ipfix/ipfix:exportingProcess/ipfix:destination'
        + '/ipfix:DestinationParameters/ipfix:tcpExporter'
        + '/ipfix:tcpExporter' {
    description
      "Augments the tcpExporter data within the destination list of
       the IPFIX exportingProcess list.";

    leaf fqdn {
      type inet:domain-name;
      description "FQDN of the Collection Process to which IPFIX Messages are sent (A resolution will first take place to get the resolved IPs).";
    }

    leaf username {
      type string {
        length "5..16";
      }
      must "../nokia-ipfix:password" {
          error-message "Password is mandatory to configure username.";
          description "Password is mandatory when username is configured.";
      }
      description
       "Username to be sent in the first template while communicating
        with the collector. This is used by the collector to validate
        the exporter. If username received by the collector does not
        match the expected value, collector will terminate the session
        with the exporter.";
    }

    leaf password {
      type ianach:crypt-hash;
      must "../nokia-ipfix:username" {
        error-message "Username is mandatory to configure password.";
        description "Username is mandatory when configuring the password.";
      }
      description
        "Password to be sent in the first template while communicating
         with the collector. This is used by the collector to validate
         the exporter. If password received by the collector does not
         match the expected value, collector will terminate the
         session with the exporter. SHA-512 hashing algorithm will be
         used for encryption.";
    }

    container certificate {
        presence "Provisioning of certificates";
        description
            "A reusable grouping for configuring a TLS client without
            any consideration for how an underlying TCP session is
            established.";
        uses tlsc:tls-client-grouping;
    }
  }

  typedef status {
    type enumeration {
      enum Connected {
        description
          "This value indicates that the connection from Exporter
           to Collector is successful";
      }
      enum Disconnected {
        description
          "This value indicates that the existing connection
           between Exporter and Collector is disconnected";
      }
      enum UnableToConnect {
        description
          "This value indicates that the Exporter is unable
           to connect to the Collector";
      }
    }
    description "The status of the connection between Exporter and Collector.";
  }

  notification collector-connection-status {
    description
      "A notification to report the status of the
       connection to Collector";

    leaf destinationName {
      type string;
      description
        "This parameter contains the name of the Collector";
    }

    leaf destinationAddress {
      type union {
         type inet:ip-address;
         type inet:domain-name;
      }
      description
        "This parameter contains the IP address or the FQDN value of the Collector";
    }

    leaf destinationPort {
      type inet:port-number;
      description
        "This parameter contains the port number of the Collector";
    }

    leaf status {
      type status;
      description
        "This parameter contains the status of the connection
         between Exporter and Collector";
    }

    leaf reason {
      type string;
      description
        "This parameter contains the reason for different
         connection status.
         Possible reasons for status Disconnected,
           (i)Triggered by IPFIX Collector,
           (ii)Triggered by Operator.";
    }

    leaf date-and-time {
      type yang:date-and-time;
      description
         "This parameter contains the timestamp of the
          connection status change from Exporter to Collector";
    }
  }

  notification ipfix-configuration-error {
    description
      "A notification indicating that there is an ipfix configuration error";

    leaf reason {
       type string;
       description
         "Configuration error reason, e.g., it's during
          replay phase";
    }

    leaf details {
       type string;
       description
         "Detailed description of the configuratios errors, e.g., wrong xpath,
          illegal exporting interval, etc";
    }
  }
}
