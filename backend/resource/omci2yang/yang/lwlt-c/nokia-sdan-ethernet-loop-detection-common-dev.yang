module nokia-sdan-ethernet-loop-detection-common-dev {
  yang-version 1.1;
  namespace "http://www.nokia.com/Fixed-Networks/BBA/yang/"
           + "nokia-sdan-ethernet-loop-detection-common-dev";
  prefix eld-dev;

  import nokia-sdan-ethernet-loop-detection {
    prefix nokia-sdan-eld;
  }

  import ietf-interfaces {
    prefix if;
  }

  import bbf-interface-usage {
    prefix bbf-if-usg;
  }

  import iana-if-type {
    prefix ianaift;
  }

  organization
    "Nokia";

  contact
    "Comments or questions about this Nokia YANG module should be
     directed to <mailto:isam.yang@nokia.com>.";

  description
    "This module contains a collection of YANG definitions for
     supporting Nokia specific requirements as applicable to its
     access network equipment.

     Specifically, this module defines configuration and operational
     state data for ethernet loop detection.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

  revision 2024-11-06 {
    description
      "Initial revision.";
    reference
      "Nokia specific.";
  }

  deviation "/nokia-sdan-eld:ethernet-loop-detection/"+
            "nokia-sdan-eld:interfaces/nokia-sdan-eld:name" {
    description
      "Ethernet loop detection can be enabled only on upink port.";
    deviate add {
      must "(/if:interfaces/if:interface[if:name = current()]/if:type"+
           " = 'ianaift:ethernetCsmacd') and (/if:interfaces/if:interface"+
           "[if:name = current()]/bbf-if-usg:interface-usage/bbf-if-usg:"+
           "interface-usage = 'network-port')" {
        error-message
            "Loop detection is supported only on Uplink port.";
      }
    }
  }


  deviation "/nokia-sdan-eld:ethernet-loop-detection/nokia-sdan-eld"+
            ":interfaces/nokia-sdan-eld:vlan-list" {
    description
      "Only one VLAN list is supported.";
    deviate add {
      max-elements 1;
    }
  }

  deviation "/nokia-sdan-eld:ethernet-loop-detection/"+
            "nokia-sdan-eld:interfaces/nokia-sdan-eld:vlan-list/"+
            "nokia-sdan-eld:vlan-tag/nokia-sdan-eld:index" {
    description "Index 0 represents the outer VLAN, and Index 1 represents the inner VLAN. However, at present, only Index 0 (outer VLAN) is supported.";
    deviate replace {
      type uint8 {
        range "0";
      }
    }
  }

  deviation "/nokia-sdan-eld:ethernet-loop-detection/"+
            "nokia-sdan-eld:interfaces/nokia-sdan-eld:vlan-list/"+
            "nokia-sdan-eld:vlan-tag/nokia-sdan-eld:pbit" {
    description "Not supported in current feature scope.";
    deviate not-supported;
  }

  deviation "/nokia-sdan-eld:ethernet-loop-detection/"+
            "nokia-sdan-eld:interfaces/nokia-sdan-eld:vlan-list/"+
            "nokia-sdan-eld:vlan-tag/nokia-sdan-eld:dei" {
    description "Not supported in current feature scope.";
    deviate not-supported;
  }
}
