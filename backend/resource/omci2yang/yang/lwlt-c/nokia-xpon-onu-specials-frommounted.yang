module nokia-xpon-onu-specials-frommounted {
  yang-version 1.1;
  namespace "urn:bbf:yang:nokia-xpon-onu-specials-frommounted";
  prefix nokia-xpon-onu-specials-frommounted;

  import ietf-interfaces-frommounted {
    prefix if-frommounted;
  }



  import bbf-fiber-onu-emulated-mount {
     prefix onu;
  }

  organization
    "Nokia
     PON Management Project Stream";

  contact
    "Comments or questions about this YANG module
     should be directed to

     Editor:      Robert Peschi, Nokia";

  description
    "YANG module for xPON ONU for managing the Link Pass Through Mode(LPT).

     Copyright (c) 2020, Nokia of America Corporation

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385; see
     the TR itself for full legal notices.";
     
   revision 2022-07-20 {
    description
      "Initial revision .";
    reference
      "TBD";
  }    
     

  revision 2020-05-04 {
    description
      "Initial revision.";
    reference
      "TBD";
  }

  augment "/onu:onus/onu:onu/onu:fromroot/if-frommounted:interfaces/if-frommounted:interface" {
   description "augment ethernet interface";
   
   leaf disable-upon-ponlos {
      type boolean ;
      description
        "This YANG leaf applies to an interface, which
         is a physical UNI, an onu-v-venet interface
         or a onu-v-refpoint interface of an ONU
         (the latter sometimes being called VEIP).
         When true, this YANG leaf makes the oper-status
         of such an interface to become down, as long
         as the ONU ANI suffers from a PON LOS condition.
         In case of a physical UNI, the transmitter
         of the physical port under the UNI is also
         switched-off during the PON LOS condition.
         When false, this YANG leaf has no impact on
         the interface nor on the underlying physical
         port, in case of a physical UNI.";
   }
  }
}
