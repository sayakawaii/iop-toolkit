module nokia-bbf-software-image-management-one-dot-one-mounted-eonu-dev {

  namespace
    "http://www.nokia.com/Fixed-Networks/BBA/yang/nokia-bbf-software-image-management-one-dot-one-mounted-eonu-dev";

  prefix "nokia-bbf-software-image-management-one-dot-one-mounted-eonu-dev";

  import bbf-fiber-onu-emulated-mount {
    prefix onu;
  }

  import bbf-software-image-management-one-dot-one-mounted {
     prefix bbf-sim-mounted;
  }

  import ietf-hardware-mounted {
    prefix hw-mounted;
  }

  import bbf-yang-types {
    prefix bbf-yang;
  }

  organization
       "BBF/NOKIA";

  contact
       "Comments or questions about this Nokia YANG module should be
       directed to <mailto:isam.yang@nokia.com>.";

  description
      "bbf-software-image-managent YANG module supporting
       deviations.
       This specification is published by Nokia under Non-Disclosure
       Agreement(s) (NDA) with specific parties and has to be considered
       as Confidential Information as defined in such NDA. Nokia
       reserves the right to revise this document for any reason,
       including but not limited to conformity with standards
       promulgated by various agencies, utilisation of advances in the
       state of the technical areas, or the reflection of changes in the
       design of any equipment, techniques, or procedures described or
       referred to herein.

       The product specifications and other technical or performance
       information contained herein are subject to change without
       notice. Updates of this document will be issued under the above
       NDA's.

       Nokia makes no representation or warranty, expressed or implied,
       with respect to the sufficiency, accuracy, or utility of any
       information or opinion contained herein. Nokia expressly advises
       that any use of for any purpose or reliance upon this technical
       reference is at the risk of the user and that Nokia shall not be
       liable for any damage or injury incurred by any person arising
       out of the sufficiency, accuracy, or utility of any information
       or opinion contained herein.

       This document is not to be construed as a suggestion to any
       manufacturer to modify or change any of its products, nor does
       this document represent any commitment by Nokia to sell or
       purchase any product. Nothing contained herein shall be construed
       as conferring by implication, estoppel, or otherwise any license
       or right under any patent, whether or not the use of any
       information herein necessarily employs an invention of any
       existing or later issued patent.

       Nokia reserves the right not to offer any or all of these
       products and to withdraw any or all of them at any future time.

       Copyright (C) 2017, Nokia. All Rights Reserved.";

  /* revision */
  revision 2021-04-08 {
    description
      "1. Adding deviaiton for file name length
       2. Changing name to follow naming conventions";
    reference
      "Nokia specific";
  }

  revision 2019-05-10 {
    description
      "added leaf server-public-key in
       nokia-software-image-management-extension.yang";
    reference
      "Nokia specific";
  }

  revision 2019-04-23 {
    description
      "Rename and move to swm category.";
    reference
      "TBD";
  }

  revision 2018-11-29 {
    description
      "corrected the errors in comment section in
       bbf-software-image-management-one-dot-one-dev.yang file";
    reference
      "Nokia specific";
  }

  revision 2018-09-21 {
    description
      "added base type as failure-reason to identity no-failure";
    reference
      "TBD";
  }

  revision 2018-08-16 {
    description
      "Initial revision.";
    reference
      "TBD";
  }


/* deviations for length of the URL */
/* -----------------------------*/
/* url is one of the input parameters for */
/* action: download */
/* length of url is restricted to 255 characters */

 deviation "/onu:onus/onu:onu/onu:root/hw-mounted:hardware-state/hw-mounted:component/bbf-sim-mounted:software/bbf-sim-mounted:software/bbf-sim-mounted:download/bbf-sim-mounted:download-software/bbf-sim-mounted:input/bbf-sim-mounted:download-method/bbf-sim-mounted:url/bbf-sim-mounted:url" {
    description
       "This deviaton assures that URL length is restricted to 255 chars.";
    deviate replace {
      type string {
          length "1..255";
      }
    }
 }

 /* deviations for user provided software name */
 /* -----------------------------------------*/
 /* name is one of the input parameters for */
 /* action: download */
 /* name is restricted to have alphanumeric characters */
 /* and only three special characters "-_." */

 deviation "/onu:onus/onu:onu/onu:root/hw-mounted:hardware-state/hw-mounted:component/bbf-sim-mounted:software/bbf-sim-mounted:software/bbf-sim-mounted:download/bbf-sim-mounted:download-software/bbf-sim-mounted:input/bbf-sim-mounted:name" {
    description
       "This deviaton assures that sw-name contains specific alphanumeric and special chars.";
    deviate replace {
      type bbf-yang:string-ascii64 {
           pattern '[-a-zA-Z0-9_.]*';
      }
    }
  }

 /* deviations for user provided software name */
 /* -----------------------------------------*/
 /* name is one of the input parameters for */
 /* action: abort */
 /* name is restricted to have alphanumeric characters */
 /* and only three special characters "-_." */

 deviation "/onu:onus/onu:onu/onu:root/hw-mounted:hardware-state/hw-mounted:component/bbf-sim-mounted:software/bbf-sim-mounted:software/bbf-sim-mounted:download/bbf-sim-mounted:abort-download/bbf-sim-mounted:input/bbf-sim-mounted:name" {
    description
       "This deviaton assures that sw-name contains specific alphanumeric and special chars.";
    deviate replace {
      type bbf-yang:string-ascii64 {
               pattern '[-a-zA-Z0-9_.]*';
      }
    }
  }

  /* deviations for user provided software name */
 /* -----------------------------------------*/
 /* sw-name should not be more than 14 characters long */

 deviation '/onu:onus/onu:onu/onu:root/hw-mounted:hardware-state/hw-mounted:component/bbf-sim-mounted:software/bbf-sim-mounted:software/bbf-sim-mounted:download'
          +'/bbf-sim-mounted:download-software/bbf-sim-mounted:input/bbf-sim-mounted:name' {
   description
       "This deviaton assures that sw-name should not be more than 14 chras long.";
   deviate replace {
     type string {
       length "1..14";
     }
   }
  }

}
