module nokia-sdan-voice-pm-threshold-profiles-mounted {
  yang-version 1.1;
  namespace "http://www.nokia.com/Fixed-Networks/BBA/yang/"
           + "nokia-sdan-voice-pm-threshold-profiles-mounted";
  prefix nokia-voice-pm-threhsold-profiles-mounted;
  import bbf-yang-types {
    prefix bbf-yang;
  }
  import nokia-yang-types-mounted {
    prefix nok-typ-mounted;
  }
  import nokia-hardware-profiles-mounted {
    prefix nokia-hw-prof-mounted;
  }
  import nokia-sdan-hardware-pm-threshold-profiles-mounted {
    prefix nokia-hw-pm-threshold-prof-mounted;
  }
  import bbf-fiber-onu-emulated-mount {
    prefix onu;
  }
  organization
    "Nokia";
  contact
    "Comments or questions about this Nokia YANG module should be
     directed to <mailto:isam.yang@nokia.com>.";
  description
    "This module contains a collection of YANG definitions for
     supporting Nokia specific requirements as applicable to its
     access network equipment.
     This module, in particular, augments the performance monitoring threshold
     profiles with data that allows you to configure thresholding values for
     performance data associated with Ethernet counters.
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.
     The product specifications and other technical or performance
     information contained herein are subject to change without
     notice. Updates of this document will be issued under the above
     NDA's.
     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
     Nokia reserves the right not to offer any or all of these
     products and to withdraw any or all of them at any future time.
     Copyright (C) 2022, Nokia. All Rights Reserved.";
  revision 2022-12-02 {
    description
      "Implementation of threshold profiles to associate with Voice performance monitoring counters.";
    reference
      "G.988";
  }
  identity pots-pm-tca-alert {
    description
      "Indicates which POTS performance monitoring TCA element has reached the configured
       threshold within the current interval";
  }
  identity pots-pm-tca-call-setup-failure{
    base pots-pm-tca-alert;
    description
      "Indicates that the number of call setup failures have reached the configured threshold value
       within the current interval";
  }
  identity pots-pm-tca-call-setup-timeout{
    base pots-pm-tca-alert;
    description
      "Indicates that the number of call setup timeouts have reached the configured threshold value
       within the current interval";
  }
  identity pots-pm-tca-call-terminate{
    base pots-pm-tca-alert;
    description
      "Indicates that the number of calls that were terminated have reached the configured threshold value
       within the current interval";
  }
  identity pots-pm-tca-port-release {
    base pots-pm-tca-alert;
    description
      "Indicates that the number of analogue port releases without dialing detected, have reached the
      configured threshold value within the current interval";
  }
  identity pots-pm-tca-port-offhook-timeout {
    base pots-pm-tca-alert;
    description
      "Indicates that the number of single offhooks detected have reached the configured threshold
       value within the current interval";
  }
  identity pots-pm-tca-rtp-errors {
    base pots-pm-tca-alert;
    description
      "Indicates that the number of RTP packet errors have reached the configured threshold
       value within the current interval";
  }
  identity pots-pm-tca-rtp-packet-loss {
    base pots-pm-tca-alert;
    description
      "Indicates that the RTP lost packet count has reached the configured threshold
       value within the current interval";
  }
  identity pots-pm-tca-rtp-max-jitter {
    base pots-pm-tca-alert;
    description
      "Indicates that the maximum jitter identified in RTP timestamp units has reached the configured threshold
       value within the current interval";
  }
  identity pots-pm-tca-rtcp-inter-pkt-time {
    base pots-pm-tca-alert;
    description
      "Indicates that the maximum time between the RTCP packets has reached the configured threshold
       value within the current interval";
  }
  identity pots-pm-buffer-underflow {
    base pots-pm-tca-alert;
    description
      "Indicates that the number of times the RTP reassembly buffer has underflown, has reached the configured threshold
       value within the current interval";
  }
  identity pots-pm-buffer-overflow {
    base pots-pm-tca-alert;
    description
      "Indicates that the number of times the RTP reassembly buffer has overflown, has reached the configured threshold
       value within the current interval";
  }

  augment "/onu:onus/onu:onu/onu:root/nokia-hw-prof-mounted:tca-profiles/nokia-hw-pm-threshold-prof-mounted:pm-profiles" {
      description "augment pm profile";
      list ccpm-failure-profile {
        key "name";
        description
            "TCA profile to configure threshold values for POTS interworking call control performance monitoring failures";
        leaf name {
          type nok-typ-mounted:nokia-string-ascii64;
          description
            "Name of the TCA profile that can be associated to POTS interworking node to notify
            TCA when the PM counter values crosses the configured threshold";
        }
        leaf call-setup-fail-threshold {
            type bbf-yang:performance-counter64;
            description
              "Threshold value for number of call setup failures. When the call setup failures crosses
              the threshold, a TCA is raised";
        }
        leaf call-setup-timeout-threshold {
            type bbf-yang:performance-counter64;
            units "milliseconds";
            description
              "Threshold value for the call setup timeouts. When time to setup a call in milliseconds, crosses
              the threshold, a TCA is raised";
        }
        leaf call-terminate-threshold {
            type bbf-yang:performance-counter64;
            description
              "Threshold value for the the number of calls that were terminated with cause. When the number of call terminate
              failures crosses the threshold, a TCA is raised";
        }
        leaf port-release-no-dialing-threshold {
           type bbf-yang:performance-counter64;
           description
             "Threshold value for number of analogue port releases without dialling detected. When the count crosses the
             threshold, a TCA is raised";
        }
         leaf port-offhook-timeout-threshold {
           type bbf-yang:performance-counter64;
           units "milliseconds";
           description
             "Threshold value for the longest period (in milliseconds) of a single off-hook detected on the analogue port
             When the time crosses the threshold, a TCA is raised";
        }
      }
      list rtp-failure-profile {
        key "name";
        description
         "TCA profile to configure threshold values for POTS interworking RTP performance monitoring failures";
        leaf name {
          type nok-typ-mounted:nokia-string-ascii64;
          description
            "Name of the TCA profile that can be associated to POTS interworking node to notify
            TCA when the PM counter values crosses the configured threshold";
        }
        leaf rtp-errors-threshold {
          type bbf-yang:performance-counter64;
          description
           "Threshold value for RTP packet errors. When the RTP error count crosses the threshold, a TCA is raised";
        }
        leaf rtp-packet-loss-threshold {
          type bbf-yang:performance-counter64;
          description
           "Threshold value for RTP packet loss. When the number of lost RTP packet crosses the threshold, a TCA is raised";
        }
        leaf max-jitter-threshold {
          type bbf-yang:performance-counter64;
          units "RTP timestamp units";
          description
           "Threshold value for the maximum jitter identified during the measured interval, expressed in RTP timestamp units.
           When the maximum jitter crosses the threshold, a TCA is raised";
        }
        leaf max-rtcp-inter-packet-time-threshold {
          type bbf-yang:performance-counter64;
          units "milliseconds";
          description
           "Threshold value for the maximum time between RTCP packets during the measured interval, in millisecond
           When the maximum time between the RTCP packets crosses the threshold, a TCA is raised";
        }
        leaf buffer-underflow-threshold {
          type bbf-yang:performance-counter64;
          description
           "Threshold value for the number of times the RTP reassembly buffer underflows.
           When the number of buffer underflow crosses the threshold, a TCA is raised";
        }
        leaf buffer-overflow-threshold {
          type bbf-yang:performance-counter64;
          description
           "Threshold value for the number of times the RTP reassembly buffer overflows.
           When the number of buffer overflow crosses the threshold, a TCA is raised";
        }
      }
  }
}
