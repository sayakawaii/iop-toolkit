module nokia-dhcpv4-relay-agent-extn {
  yang-version 1.1;
  namespace "http://www.nokia.com/Fixed-Networks/BBA/yang/"
          + "nokia-dhcpv4-relay-agent-extn";
  prefix nokia-d4r-extn;

  import bbf-l2-dhcpv4-relay {
    prefix bbf-l2-d4r;
  }

  organization
    "Nokia";

  contact
    "Comments or questions about this Nokia YANG module should be
     directed to <mailto:isam.yang@nokia.com>.";

  description
    "This module contains a collection of YANG definitions for
     supporting Nokia specific requirements as applicable to its
     access network equipment.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2020, Nokia. All Rights Reserved.";

  revision 2020-11-18 {
    description
 
      "add-or-forward leaf inclusion.
       * Approval Date:    see revision date above.
       * Publication Date: yyyy-mm-dd.";
    reference
      "Nokia specific";
  }

  revision 2020-06-23 {
    description
      "Initial revision.
       * Approval Date:    see revision date above.
       * Publication Date: yyyy-mm-dd.";
    reference
      "Nokia specific";
  }

  identity tag-handling-option {
    description
     "Base identity for defining option-82 tag handling in DHCPv4
      messages received.
      This is an abstract identity and MUST NOT be used for
      option-82 tag handling attributes.";
  }

  identity upstream-tag-replace {
    base tag-handling-option;
    description
      "Base identity for defining replacement of option-82 tag in
       upstream DHCPv4 messages received with option-82 tag.";
  }

  identity  add-or-forward{
    base tag-handling-option;
    description
      "Base identity for defining insertion of option-82 tag in
       upstream DHCPv4 messages received without option-82 tag.
       option-82 tag includes insertion of Relay Agent ID
       sub-option 0x12. This sub-option values field inserts
       with System MAC address for unique identification of Access Node.
 
       upstream packet received with option-82 tag forwarded without
       modification.

       This field also defines removal of option-82 tag in downstream
       DHCPv4 messages received with option-82. option-82 tag shall
       be stripped based on matching Relay Agent ID sub-option 0x12
       value. Packet shall be forward without option-82 tag removal
       when sub-option 0x12 value does not matches";
  }

  grouping tag-handling-options {
    description
      "Defines the configuration of option-82 tag handling in
       DHCPv4 messages received.";

    leaf option82-handling-extn {
      type identityref {
        base tag-handling-option;
      }
      description
        "Defines the configuration of option-82 tag handling in
         DHCPv4 messages received with option-82 tag. when this
         leaf is not configured, DHCPv4 messages received with
         option-82 tag in upstream direction gets discarded.";
    }
  }

  augment
    "/bbf-l2-d4r:l2-dhcpv4-relay-profiles" +
    "/bbf-l2-d4r:l2-dhcpv4-relay-profile" {
    description
      "Augments the configuration of the DHCPv4 relay profile with
       option-82 tag handling configuration.";

      uses tag-handling-options;
  }
}
