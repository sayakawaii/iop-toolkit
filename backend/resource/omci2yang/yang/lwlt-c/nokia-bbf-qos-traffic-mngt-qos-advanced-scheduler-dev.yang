module nokia-bbf-qos-traffic-mngt-qos-advanced-scheduler-dev {

  namespace
    "http://www.nokia.com/Fixed-Networks/BBA/yang/nokia-bbf-qos-traffic-mngt-qos-advanced-scheduler-dev";

  prefix  nokia-bbf-qos-traffic-mngt-qos-advanced-scheduler-dev;

  import bbf-qos-traffic-mngt {  
    prefix bbf-qos-tm;
  }
  
  import ietf-interfaces {
    prefix if;
  }
  
  import bbf-xpon-if-type {
    prefix bbf-xponift;
  }
  
  import iana-if-type {
    prefix ianaift;
  }

  organization
    "Nokia";

  contact
    "isam.yang@nokia.com";

  description
    "This module contains a collection of YANG deviations on top 
     of standard for supporting BBF/bbf-qos-traffic-mgnt YANG module.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017-2018, Nokia. All Rights Reserved.";

  /* revision */
  revision 2025-03-28 {
    description
      "Move queue id check for uplink interface to other categories";
    reference
      "Nokia specific";
  }
  
  revision 2023-08-15 {
    description
      "Remove a deviation to allow any tc2q profile names.";
    reference
      "Nokia specific";
  }

  revision 2019-03-28 {
    description
      "Initial revision.";
    reference
      "Nokia specific";
  }
  
  deviation "/if:interfaces/if:interface/bbf-qos-tm:tm-root/bbf-qos-tm:children-type/bbf-qos-tm:queues/bbf-qos-tm:queue"{
    deviate add {
       must "current()/../../if:type = 'bbf-xponift:channel-partition' or current()/../../if:type = 'ianaift:ethernetCsmacd'" {
         error-message "Only channel-partition or ethernetCsmacd type interface can configure tm-root.";
       }
    }
  }
    
  deviation "/if:interfaces/if:interface/bbf-qos-tm:tm-root/bbf-qos-tm:tc-id-2-queue-id-mapping-profile-name"{
    deviate add {
       must "current()/../../if:type = 'bbf-xponift:channel-partition' or current()/../../if:type = 'ianaift:ethernetCsmacd'" {
         error-message "Only channel-partition or ethernetCsmacd type interface can configure tm-root.";
       }
    }
  }
  
}
