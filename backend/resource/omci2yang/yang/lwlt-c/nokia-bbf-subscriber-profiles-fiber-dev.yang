module nokia-bbf-subscriber-profiles-fiber-dev {

  namespace "http://www.nokia.com/Fixed-Networks/BBA/yang/"
            + "nokia-bbf-subscriber-profiles-fiber-dev";

  prefix nokia-bbf-subscriber-profiles-fiber-dev;

  import ietf-interfaces {
    prefix if;
  }

  import bbf-subscriber-profiles {
    prefix bbf-subprof;
  }

  import bbf-if-type {
    prefix bbfift;
  }

  import bbf-xpon-if-type {
    prefix bbf-xponift;
  }

  organization
    "Nokia";

  contact
    "Comments or questions about this Nokia YANG module should be
     directed to <mailto:isam.yang@nokia.com>.";

  description
    "This module contains a collection of YANG deviations on top
     of the standard bbf-subscriber-profiles.yang module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2021-12-16 {
    description
      "Addition of olt-v-ent interface type for subscriber profile association";
    reference
      "Nokia specific";
  }

  revision 2021-10-26 {
    description
      "Initial revision.";
    reference
      "Nokia specific";
  }

  /**************************************************************/
  /* subscriber-profile can be associated to an interface of type
     VLAN sub-interface, VANI interface and OLT-V-ENET interface */
  /**************************************************************/

  deviation "/if:interfaces/if:interface/bbf-subprof:subscriber-profile/bbf-subprof:profile" {
    deviate add {
      must "((current()/../../if:type = 'bbfift:vlan-sub-interface')"
      +" or (current()/../../if:type = 'bbf-xponift:v-ani')"
      +" or (current()/../../if:type = 'bbf-xponift:olt-v-enet'))"
       {
        error-message "subscriber-profile can be associated only on vlan-sub-interface, v-ani interfaces and olt-v-enet interfaces";
        description
             "subscriber-profile can be associated to an interface of type VLAN sub-interface, VANI interface and OLT-V-ENET interfaces";
      }
    }
  }
}
