module nokia-sdan-802dot1x-frommounted {

  namespace "http://www.nokia.com/Fixed-Networks/BBA/yang/"
          + "nokia-sdan-802dot1x-frommounted";

  prefix "dot1x-frommounted";

  import bbf-fiber-onu-emulated-mount {prefix onu;}
  import ietf-interfaces-frommounted { prefix "if-frommounted"; }

  organization
    "Nokia";

  contact
    "Comments or questions about this Nokia YANG module should be
     directed to <mailto:isam.yang@nokia.com>.";

  description
    "This module contains a collection of YANG definitions for
     supporting Nokia specific requirements as applicable to its
     access network equipment.

     Port-based network access control allows a network administrator
     to restrict the use of IEEE 802 LAN service access points (ports)
     to secure communication between authenticated and authorized
     devices. IEEE Std 802.1X specifies an architecture, functional
     elements, and protocols that support mutual authentication
     between the clients of ports attached to the same LAN and secure
     communication between the ports. The following control allows a
     port to be reinitialized, terminating (and potentially
     restarting) authentication exchanges and MKA operation, based on
     a data model described in a set of YANG modules.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2022-01-20 {
    description
      "Initial revision.
       * Approval Date:    see revision date above.
       * Publication Date: yyyy-mm-dd.";
    reference
      "Nokia specific";
  }

  /* ----------------------------------------------
   * Type definitions used by dot1X YANG module
   * ----------------------------------------------
   */

  grouping port-capabilities {
    description
      "Per port PAE feature capabilities.";
    leaf auth {
      type boolean;
      description
        "Indicates if PACP EAP Authenticator is supported.";
      reference
        "IEEE 802.1X-2010 Clause 12.9.2";
    }
  }


  /*
   *  Port Authentication Entity (PAE) Nodes
   */
  augment "/onu:onus/onu:onu/onu:fromroot/if-frommounted:interfaces/if-frommounted:interface" {


    description
      "Augment interface model with PAE configuration nodes.";
    reference
      "IEEE 802.1AE Clause 11.7 and IEEE 802.1X-2010 Clause 6.5 and
      Clause 13.3.2";
    container pae {
      presence "pae";
      description
        "Contains PAE configuration related nodes.";

      container port-capabilities {
        presence "port-capabilities";
        description
          "Per port PAE feature capabilities.";
        uses port-capabilities;
      }
    }
  }
}
