module nokia-bbf-l2-forwarding-inexpressible-constraints-qos-fiber-xpon-hwv3-dev {

  yang-version "1.1";
  namespace "http://www.nokia.com/Fixed-Networks/BBA/yang/"
            + "nokia-bbf-l2-forwarding-inexpressible-constraints-qos-fiber-xpon-hwv3-dev";

  prefix nokia-bbf-l2-forwarding-inexpressible-constraints-qos-fiber-xpon-hwv3-dev;

  import bbf-l2-forwarding {
    prefix bbf-l2-fwd;
  }
  
  organization
    "NOKIA";

  contact
    "Comments or questions about this Nokia YANG module should be
     directed to <mailto:isam.yang@nokia.com>.";

  description
    "The NOKIA common/nokia-bbf-l2-forwarding-inexpressible-constraints-qos-fiber-xpon-hwv3-dev
     YANG module supporting deviations on top of ietf-ssh-server standard.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2019, Nokia. All Rights Reserved.";

  revision 2017-04-24 {
    description
      "Initial revision.";
    reference
      "Nokia specific"; 
  }

  deviation "/bbf-l2-fwd:forwarding/bbf-l2-fwd:forwarders/bbf-l2-fwd:forwarder" {
    description
      "The detailed restrictions: 1. The marker policy should use 'vlan tag 0 in-pbit-list' or 'pbit-marking-list 0' as filter.
2. If there is no marker policy to create metadata to determine p-bit values to write to a VLAN tag, then CCL policy/Pre-handling-entry/Scheduler policy/Queue-color policy should use 'vlan tag 0 in-pbit-list' or 'pbit-marking-list 0' as filter.
3. If there is a marker policy to create metadata to sepecify p-bit values to write to VLAN tag 0, then CCL policy should use 'vlan tag 0 in-pbit-list' or 'pbit-marking-list 0' as filter, and Pre-handling-entry/Scheduler policy/Queue-color policy should use 'vlan tag 0 in-pbit-list' or 'pbit-marking-list 0' as filter.
4. If there is a marker policy to create metadata to sepecify p-bit values to write to VLAN tag 0 and VLAN tag 1, then CCL policy should use 'vlan tag 0 in-pbit-list' or 'pbit-marking-list 0' as filter, and Pre-handling-entry should use 'vlan tag 1 in-pbit-list' or 'pbit-marking-list 1' as filter, and Scheduler policy/Queue-color policy should use 'vlan tag 0 in-pbit-list' or 'pbit-marking-list 0' as filter.
Dei filter has the same restrictions.

       Other dependent xpaths where this rule applies are:
        '/bbf-l2-fwd:forwarding/bbf-l2-fwd:forwarders/bbf-l2-fwd:forwarder/bbf-l2-fwd:ports/bbf-l2-fwd:port'
        '/if:interfaces/if:interface'
        '/bbf-qos-pol:qos-policy-profiles/bbf-qos-pol:policy-profile'
        '/bbf-qos-pol:policies/bbf-qos-pol:policy'
        '/bbf-qos-cls:classifiers/bbf-qos-cls:classifier-entry'
        '/bbf-qos-plc:policing-profiles/bbf-qos-plc:policing-profile'
        '/bbf-qos-filt:filters/bbf-qos-enhfilt:enhanced-filter'
        '/nokia-qos-plc-ext:policing-pre-handling-profiles/nokia-qos-plc-ext:pre-handling-profile'
        '/bbf-frameproc:frame-processing-profiles/bbf-frameproc:frame-processing-profile'
       The error message 'For ingress policies of user VSI which attached to a dual tag forwarder, the pbit and dei filters have vlan tag reference restrictions.' will be displayed when the constraint is violated.";
    deviate add {}
  }
  
  deviation "/bbf-l2-fwd:forwarding/bbf-l2-fwd:forwarders/bbf-l2-fwd:forwarder" {
    description
      "Other dependent xpaths where this rule applies are:
        '/bbf-l2-fwd:forwarding/bbf-l2-fwd:forwarders/bbf-l2-fwd:forwarder/bbf-l2-fwd:ports/bbf-l2-fwd:port'
        '/if:interfaces/if:interface'
        '/bbf-qos-pol:qos-policy-profiles/bbf-qos-pol:policy-profile'
        '/bbf-qos-pol:policies/bbf-qos-pol:policy'
        '/bbf-qos-cls:classifiers/bbf-qos-cls:classifier-entry'
        '/bbf-qos-plc:policing-profiles/bbf-qos-plc:policing-profile'
        '/bbf-qos-filt:filters/bbf-qos-enhfilt:enhanced-filter'
        '/nokia-qos-plc-ext:policing-pre-handling-profiles/nokia-qos-plc-ext:pre-handling-profile'
        '/bbf-frameproc:frame-processing-profiles/bbf-frameproc:frame-processing-profile'
       The error message 'For policies except CCL configured in egress qos policy profile of user VSI which attached to a dual tag forwarder, they can only reference inner or outer vlan tag.' will be displayed when the constraint is violated.";
    deviate add {}
  }
  
  deviation "/bbf-l2-fwd:forwarding/bbf-l2-fwd:forwarders/bbf-l2-fwd:forwarder" {
    description
      "Other dependent xpaths where this rule applies are:
        '/bbf-l2-fwd:forwarding/bbf-l2-fwd:forwarders/bbf-l2-fwd:forwarder/bbf-l2-fwd:ports/bbf-l2-fwd:port'
        '/if:interfaces/if:interface'
        '/bbf-qos-pol:qos-policy-profiles/bbf-qos-pol:policy-profile'
        '/bbf-qos-pol:policies/bbf-qos-pol:policy'
        '/bbf-qos-cls:classifiers/bbf-qos-cls:classifier-entry'
        '/bbf-qos-plc:policing-profiles/bbf-qos-plc:policing-profile'
        '/bbf-qos-filt:filters/bbf-qos-enhfilt:enhanced-filter'
        '/nokia-qos-plc-ext:policing-pre-handling-profiles/nokia-qos-plc-ext:pre-handling-profile'
        '/bbf-frameproc:frame-processing-profiles/bbf-frameproc:frame-processing-profile'
       The error message 'For enhanced filters referenced by CCL policy configured in egress qos policy profile of the VSI which attached to a dual tag forwarder, they can only reference inner or outer vlan tag.' will be displayed when the constraint is violated.";
    deviate add {}
  }
  
  deviation "/bbf-l2-fwd:forwarding/bbf-l2-fwd:forwarders/bbf-l2-fwd:forwarder" {
    description
      "Other dependent xpaths where this rule applies are:
        '/bbf-l2-fwd:forwarding/bbf-l2-fwd:forwarders/bbf-l2-fwd:forwarder/bbf-l2-fwd:ports/bbf-l2-fwd:port'
        '/if:interfaces/if:interface'
        '/bbf-qos-pol:qos-policy-profiles/bbf-qos-pol:policy-profile'
        '/bbf-qos-pol:policies/bbf-qos-pol:policy'
        '/bbf-qos-cls:classifiers/bbf-qos-cls:classifier-entry'
       The error message 'Pbit action list of ingress marker policy binded by VSIs which are attached to same forwarder should be coincident.it means,if pbit-marking-list actions exist,all indexs should be 0 ,or should be both 0 and 1.' will be displayed when the constraint is violated.";
    deviate add {}
  }
  
  deviation "/bbf-l2-fwd:forwarding/bbf-l2-fwd:forwarders/bbf-l2-fwd:forwarder" {
    description
      "For user vsi, the marker policy of ingress qos profile needs support 'copy pbit from header to meta (index0) for C to C forwarder mode', and the marker policy of egress qos profile needs support 'copy pbit from header to meta (index0) for C to C forwarder mode' and 'copy pbit from header to meta (index0 and index1) for C to S+C forwarder mode'.
       Other dependent xpaths where this rule applies are:
        '/bbf-l2-fwd:forwarding/bbf-l2-fwd:forwarders/bbf-l2-fwd:forwarder/bbf-l2-fwd:ports/bbf-l2-fwd:port'
        '/if:interfaces/if:interface'
        '/bbf-qos-pol:qos-policy-profiles/bbf-qos-pol:policy-profile'
        '/bbf-qos-pol:policies/bbf-qos-pol:policy'
        '/bbf-qos-cls:classifiers/bbf-qos-cls:classifier-entry'
        '/bbf-qos-plc:policing-profiles/bbf-qos-plc:policing-profile'
        '/bbf-qos-filt:filters/bbf-qos-enhfilt:enhanced-filter'
       The error message 'For this vsi, it only supports pbit copy pbit marker policy.' will be displayed when the constraint is violated.";
    deviate add {}
  }
  
}
