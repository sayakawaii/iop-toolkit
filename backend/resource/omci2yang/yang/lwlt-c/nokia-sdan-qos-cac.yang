module nokia-sdan-qos-cac {
  yang-version 1.1;
  namespace "http://www.nokia.com/Fixed-Networks/BBA/yang/"
          + "nokia-sdan-qos-cac";

  prefix nokia-qos-cac;

  import ietf-interfaces {
    prefix if;
  }

  import bbf-xpon-if-type {
    prefix bbf-xponift;
  }

  organization
    "Nokia";

  contact
    "Comments or questions about this Nokia YANG module should be
     directed to <mailto:isam.yang@nokia.com>.";

  description
    "This module contains a collection of YANG definitions for
     supporting Nokia specific requirements as applicable to its
     access network equipment.

     Specifically, this module adds configuration for CAC Channel
     Admission Control based on QoS parameter.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

  revision 2025-05-07 {
    description
      "Added container avail-ds-unicast-bw and moved leaf avail-ds-unicast-bw inside it.";
    reference
      "Nokia specific";
  }

  revision 2024-12-12 {
    description
      "Initial revision.
       * Approval Date:    see revision date above.
       * Publication Date: yyyy-mm-dd.";
    reference
      "Nokia specific";
  }

  typedef l2-capacity-megabit {
    type decimal64 {
      fraction-digits 3;
      range "0..max";
    }
    units "megabit/second";
    description
      "A type which represents the interface Layer2 capacity.";
  }

  augment "/if:interfaces-state/if:interface" {
    when
      'derived-from-or-self(if:type,"bbf-xponift:channel-pair")' {
      description
        "Only applicable on channel-pair interface.";
    }

    description
      "Augment channel-pair with bandwidth parameter.";
    container avail-ds-unicast-bw {
      description
        "Layer 2 Ethernet downstream bandwidth available for unicast
         services.";
      leaf avail-ds-unicast-bw {
        type l2-capacity-megabit;
        description
          "This represents the currently remaining Layer 2 Ethernet
           downstream bandwidth that is available for unicast
           services on top of those already provisioned.";
      }
    }
  }
}
