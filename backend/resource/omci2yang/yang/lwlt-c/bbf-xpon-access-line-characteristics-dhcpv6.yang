module bbf-xpon-access-line-characteristics-dhcpv6 {
  yang-version 1.1;
  namespace "urn:bbf:yang:bbf-xpon-access-line-characteristics-dhcpv6";

  prefix bbf-xpon-acc-d6r;

  import bbf-ldra {
    prefix bbf-ldra;
  }
  
  import bbf-xpon-access-line-characteristics-type {
    prefix bbf-xpon-acc-type;
  }

  organization 
    "Broadband Forum <https://www.broadband-forum.org>
     Common YANG Work Area";

  contact
    "Comments or questions about this Broadband Forum YANG module
     should be directed to <mailto:help@broadband-forum.org>.

     Editor:      Ludwig Pauwels, Nokia

     Editor:      Joey Boyd, ADTRAN

     WA Director: Sven Ooghe, Nokia

     WA Director: Joey Boyd, ADTRAN";
  
  description 
    "This module contains a collection of YANG definitions for
     xPON access line characteristic applied to DHCPv6 protocol
     frames.

     Specifically, this module augments DHCPv6 relay profile with
     xPON line characteristics applied to DHCPv6 protocol frames.
     
     Copyright (c) 2019, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please  reference the Forum IPR Policy for patent licensing terms
     <https://www.broadband-forum.org/ipr-policy>.

     Any moral rights which are necessary to exercise under the above
     license grant are also deemed granted under this license.

     This version of this YANG module is part of TR-383; see
     the TR itself for full legal notices.";
     
  reference
    "";

  revision 2019-10-16 {
    description
      "Initial revision.";
    reference
      "None.";
  }

  grouping xpon-access-line-characteristics-config-parameters-dhcpv6 {
    description
      "Defines the configuration of xPON access line characteristicss to be
       included in vendor-specific sub-option.";

    leaf-list xpon-access-loop-characteristics {
      type identityref {
        base bbf-xpon-acc-type:xpon-access-line-attribute-dhcpv6;
      }
      description
        "An access line characteristics to be included in the protocol frames
         vendor specific tag. If the list is empty the xPON-Access-Line-characteristics
         TLV will not be sent.";
      reference
        "IETF 'draft-lihawi-ancp-protocol-access-extension-03'
         clause 6.3";
    }
  }

  augment
    "/bbf-ldra:dhcpv6-ldra-profiles" +
    "/bbf-ldra:dhcpv6-ldra-profile" +
    "/bbf-ldra:options" {
    description
      "Augments the configuration of the DHCPv6 relay profile with
       xPON line characteristics.";

      uses xpon-access-line-characteristics-config-parameters-dhcpv6;
  }
}
