module nokia-sdan-li-ip-filter {
  yang-version 1.1;
  namespace "http://www.nokia.com/Fixed-Networks/BBA/yang/"
          + "nokia-sdan-li-ip-filter";
  prefix nokia-li-ip-fltr;

  import nokia-sdan-li-base {
    prefix nokia-li;
  }

  import ietf-packet-fields {
    prefix packet-fields;
  }

  organization
     "Nokia";
  contact
    "Comments or questions about this Nokia YANG module should be
     directed to <mailto:isam.yang@nokia.com>.";

  description
    "This module contains a collection of YANG definitions for
     supporting the IP filter for lawful interception.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2025, Nokia. All Rights Reserved.";

  revision 2026-01-28 {
    description
      "Description content changes to lawful intercept";
    reference
       "Nokia specific";
  }

  revision 2026-01-12 {
    description
      "Description content change to li";
    reference
       "Nokia specific";
  }

  revision 2026-01-06 {
    description
      "Augment xpath change to li";
    reference
      "Nokia specific";
  }

  revision 2025-12-24 {
    description
      "Change import name to nokia-sdan-li-base";
    reference
      "Nokia specific";
  }

  revision 2025-01-03 {
    description
      "Initial Revision";
    reference
      "Nokia specific";
  }

  augment "/nokia-li:li/nokia-li:mediation-entry"
         +"/nokia-li:stream-entry/nokia-li:filter" {
    description
      "Add filters to select traffic based on IP header fields.";
    container ip {
      presence
        "IP based filter is configured.";
      description
        "Define the IP header based filter.";
      choice ip-filter {
        mandatory true;
        description
          "We can filter a packet based on either IPv4 or IPv6
           header based filtering but not both.";
        case ipv4-header {
          container ipv4 {
            description
              "IPv4 based header filter definition.";
            uses packet-fields:acl-ipv4-header-fields;
          }
        }
        case ipv6-header {
            container ipv6 {
            description
              "IPv6 based header filter definition.";
            uses packet-fields:acl-ipv6-header-fields;
          }
        }
      }
    }
  }
}
