module nokia-debug-common-dev {
  yang-version "1.1";
  namespace "http://www.nokia.com/Fixed-Networks/BBA/yang/nokia-debug-common-dev";
  prefix nokia-debug-common-dev;

  import nokia-debug {
    prefix "nokia-debug";
  }

  import iana-tls-cipher-suite-algs {
        prefix "tlscsa";
  }
  
  organization "Nokia";

  contact
    "Comments or questions about this Nokia YANG module should be
     directed to <mailto:isam.yang@nokia.com>.";

  description
    "The NOKIA common/nokia-ietf-netconf-acm-common-dev YANG module
         supporting deviations on top of ietf-netconf-acm standard.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2026-02-10 {
    description "Initial Version";
    reference "Nokia specific";
  }

  deviation "/nokia-debug:nokia-debug/nokia-debug:setup-tls/nokia-debug:input/nokia-debug:transport/nokia-debug:tls/nokia-debug:server-auth" {
      deviate delete { must 'pinned-ca-certs or pinned-server-certs';}
  }
  
  
  deviation "/nokia-debug:nokia-debug/nokia-debug:setup-tls/nokia-debug:input/nokia-debug:transport/nokia-debug:tls/nokia-debug:server-auth/nokia-debug:pinned-server-certs" {
      description
      "Pinned server certs is no longer supported";
      deviate not-supported;
  }
  

  deviation "/nokia-debug:nokia-debug/nokia-debug:setup-tls/nokia-debug:input/nokia-debug:transport/nokia-debug:tls/nokia-debug:server-auth/nokia-debug:pinned-ca-certs" {
      deviate add {
       must "not(../est-certificate-profile)"{
          error-message "Exactly one authentication mechanism (EST certificate profile, or CA pinning) must be specified";
          description "Specify exactly one authentication mechanism (EST certificate profile or CA pinning)";
        }
      }
    }
  
   deviation "/nokia-debug:nokia-debug/nokia-debug:setup-tls/nokia-debug:input/nokia-debug:transport/nokia-debug:tls/nokia-debug:client-identity/nokia-debug:auth-type/nokia-debug:certificate/nokia-debug:certificate/nokia-debug:local-or-keystore/nokia-debug:keystore/nokia-debug:reference" {
        deviate not-supported;
    }
  
  /*
    deviation "/nokia-debug:nokia-debug/nokia-debug:transport/nokia-debug:tls/nokia-debug:client-identity/nokia-debug:auth-type/nokia-debug:certificate/nokia-debug:certificate/nokia-debug:local-or-keystore/nokia-debug:local" {
        deviate not-supported;
    }
*/

    deviation "/nokia-debug:nokia-debug/nokia-debug:setup-tls/nokia-debug:input/nokia-debug:transport/nokia-debug:port" {
        deviate add {
           must " ( . > 0 ) " {
                  error-message "0 is no valid port number";
                  description "0 is no valid port number.";
          }
        }
    }

    deviation "/nokia-debug:nokia-debug/nokia-debug:setup-tls/nokia-debug:input/nokia-debug:transport/nokia-debug:address" {
         /* multicast and broadcast address is not valid address  */
       deviate add {
            must "(not(translate(.,'0123456789','') = '...' and (substring-before(.,'.') >= 224) and (substring-before(.,'.') <= 255) and not(substring(., string-length(.) - string-length('.') +1) = '.')))"{
                error-message "224.0.0.0~255.255.255.255 are not valid";
                description "224.0.0.0~255.255.255.255 are not valid.";
            }
        }


       /* self address is not valid address  */
        deviate add {
            must "(not((substring-before(.,'.') = 127) and translate(.,'0123456789','') = '...' and not(substring(., string-length(.) - string-length('.') +1) = '.')))" {
                error-message "loopback address is not valid";
                description "loopback address is not valid.";
            }
        }

        deviate add {
             must "(current() != 'localhost')" {
                error-message "loopback address is not valid";
                description "loopback address is not valid.";
            }
        }
        
        /* 0.0.0.[0-255] is not valid address */
        deviate add {
            must "not(starts-with(.,'0.0.0.') and translate(.,'0123456789','') = '...' and not(substring(., string-length(.) - string-length('.') +1) = '.'))" {
                error-message "0.0.0.[0-255] is not valid address";
                description "0.0.0.[0-255] is not valid address.";
            }
        }

        /* Multicast address is not valid address  */
        deviate add {
            must "not(starts-with(.,'ff'))"{
                error-message "Multicast address is a not valid address";
                description "Multicast address is a not valid address.";
            }
        }

        /* Site-local address is not valid address  */
        deviate add {
            must "(substring-before(.,':') != 'fec0')"{
                error-message "Site-local address is a not valid address";
                description "Site-local address is a not valid address.";
            }
        }

        /* Loopback address is not valid address  */
        deviate add {
            must "(current() != '::1')"{
                error-message "Loopack address is not a valid address";
                description "Loopack address is not a valid address.";
            }
        }

        /* Unspecified address  */
        deviate add {
            must "(current() != '::')"{
                error-message "Unspecified address";
                description "Unspecified address.";
            }
        }
    }

     deviation "/nokia-debug:nokia-debug/nokia-debug:setup-tls/nokia-debug:input/nokia-debug:transport/nokia-debug:tls/nokia-debug:client-identity/nokia-debug:auth-type/nokia-debug:certificate/nokia-debug:certificate/nokia-debug:local-or-keystore/nokia-debug:keystore/nokia-debug:certificate-reference-choice/nokia-debug:central-keystore-reference/nokia-debug:central-keystore-reference/nokia-debug:asymmetric-key" {
         deviate add {
            must '../certificate' {
                error-message "'asymmetric-key' must be configured together with 'certificate' under 'central-keystore-reference'";
                description "'asymmetric-key' must be configured together with 'certificate' under 'central-keystore-reference'.";
            }
         }
    }


    deviation "/nokia-debug:nokia-debug/nokia-debug:setup-tls/nokia-debug:input/nokia-debug:transport/nokia-debug:tls/nokia-debug:hello-params/nokia-debug:cipher-suites/nokia-debug:cipher-suite" {
        description "The YANG identifiers of the supported ciphers ordered by descending preference";
        deviate add {
            must "(current() = 'tlscsa:tls-aes-256-gcm-sha384' or current() = 'tlscsa:tls-chacha20-poly1305-sha256'"+
                "or current() = 'tlscsa:tls-aes-128-gcm-sha256' or current() = 'tlscsa:tls-ecdhe-rsa-with-aes-256-gcm-sha384'"+
                "or current() = 'tlscsa:tls-ecdhe-rsa-with-chacha20-poly1305-sha256' or current() = 'tlscsa:tls-ecdhe-rsa-with-aes-128-gcm-sha256'"+
                "or current() = 'tlscsa:tls-ecdhe-rsa-with-aes-256-cbc-sha384' or current() = 'tlscsa:tls-ecdhe-rsa-with-aes-256-cbc-sha'"+
                "or current() = 'tlscsa:tls-rsa-with-aes-256-gcm-sha384' or current() = 'tlscsa:tls-rsa-with-aes-256-cbc-sha256'"+
                "or current() = 'tlscsa:tls-rsa-with-aes-256-cbc-sha' or current() = 'tlscsa:tls-ecdhe-rsa-with-aes-128-cbc-sha256'"+
                "or current() = 'tlscsa:tls-ecdhe-rsa-with-aes-128-cbc-sha' or current() = 'tlscsa:tls-rsa-with-aes-128-gcm-sha256'"+
                "or current() = 'tlscsa:tls-rsa-with-aes-128-cbc-sha256' or current() = 'tlscsa:tls-rsa-with-aes-128-cbc-sha')"{
                error-message "this cipher is not supported";
                description "The YANG identifiers of the supported ciphers ordered by descending preference";
            }
        }
    }

}
