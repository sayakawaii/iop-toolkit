module nokia-sdan-xpon-onu-types {
    yang-version 1.1;
    namespace "http://www.nokia.com/Fixed-Networks/BBA/yang/" +
     "nokia-sdan-xpon-onu-types";

    prefix nokia-sdan-xpon-onu-types;

    organization
        "Nokia";

    contact
        "isam.yang@nokia.com";

    description
    "This specification is published by Nokia under Non-Disclosure
    Agreement(s) (NDA) with specific parties and has to be considered
    as Confidential Information as defined in such NDA.  Nokia
    reserves the right to revise this document for any reason,
    including but not limited to conformity with standards promulgated
    by various agencies, utilization of advances in the state of the
    technical areas, or the reflection of changes in the design of any
    equipment, techniques, or procedures described or referred to
    herein.

    The product specifications and other technical or performance
    information contained herein are subject to change without notice.
    Updates of this document will be issued under the above NDA's.

    Nokia makes no representation or warranty, expressed or implied,
    with respect to the sufficiency, accuracy, or utility of any
    information or opinion contained herein. Nokia expressly advises
    that any use of for any purpose or reliance upon this technical
    reference is at the risk of the user and that Nokia shall not be
    liable for any damage or injury incurred by any person arising out
    of the sufficiency, accuracy, or utility of any information or
    opinion contained herein.

    This document is not to be construed as a suggestion to any
    manufacturer to modify or change any of its products, nor does
    this document represent any commitment by Nokia to sell or
    purchase any product. Nothing contained herein shall be construed
    as conferring by implication, estoppel, or otherwise any license
    or right under any patent, whether or not the use of any
    information herein necessarily employs an invention of any
    existing or later issued patent.

    Nokia reserves the right not to offer any or all of these products
    and to withdraw any or all of them at any future time.

    Copyright (C) 2022, Nokia. All Rights Reserved";

    revision 2025-09-23 {
        description
            "add the extended last-down-reason for v-ani.";
        reference
            "TBD";
    }

    revision 2024-04-15 {
        description
            "add the detected upstream rate of the ONU 50G.";
        reference
            "TBD";
    }

    revision 2022-07-08 {
        description
            "add the detected upstream rate of the ONU 12.5G.";
        reference
            "TBD";
    }
    
    revision 2022-01-13 {
        description
            "Initial revision.";
        reference
            "TBD";
    }

    identity detected-upstream-rate-base {
        description
            "This identity is used to define the upstream detected
            rate of the ONU."; }

    identity detected-upstream-rate-2.5 {
        base detected-upstream-rate-base;
        description
            "This identity is used to indicate the detected upstream
            rate of the ONU is 2.5G"; }

    identity detected-upstream-rate-1.25 {
        base detected-upstream-rate-base;
        description
            "This identity is used to indicate the detected upstream
            rate of the ONU is 1.25G"; }

    identity detected-upstream-rate-10 {
        base detected-upstream-rate-base;
        description
            "This identity is used to indicate the detected upstream
            rate of the ONU is 10G"; }

    identity detected-upstream-rate-12.5 {
        base detected-upstream-rate-base;
        description
            "This identity is used to indicate the detected upstream
            rate of the ONU is 12.5G"; }

    identity detected-upstream-rate-25 {
        base detected-upstream-rate-base;
        description
            "This identity is used to indicate the detected upstream
            rate of the ONU is 25G"; }

    identity detected-upstream-rate-50 {
        base detected-upstream-rate-base;
        description
            "This identity is used to indicate the detected upstream
            rate of the ONU is 50G"; }

    identity extended-down-reason-for-v-ani {
        description
            "This identity is used to extend last-down-reason
             of virtual Access Network Interface (vANI)"; }

    identity admin-down {
        base extended-down-reason-for-v-ani;
        description
            "admin-down means the reason of vANI's oper-down is due to 
             interfaces/interface/enabled set to false"; }
}
