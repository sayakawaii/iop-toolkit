module nokia-ietf-hardware-common-lwlt-c-dev {

  namespace
     "http://www.nokia.com/Fixed-Networks/BBA/yang/"
   + "nokia-ietf-hardware-common-lwlt-c-dev";

  prefix nokia-ietf-hardware-common-lwlt-c-dev;

  import ietf-hardware {
    prefix hw;
  }

  import iana-hardware {
    prefix ianahw;
  }

  import nokia-hardware-identities {
    prefix nokia-hwi;
  }

  import bbf-hardware-types {
    prefix bbf-hwt;
  }

  organization
    "Nokia";

  contact
    "Comments or questions about this Nokia YANG module should be
     directed to <mailto:isam.yang@nokia.com>.";

  description
    "The NOKIA BBF/hardware YANG module supporting
     deviations on top of standard.";
  
  revision 2025-05-15 {
    description
      "add check for model2 to skip admin-state deviation";
    reference
      "Nokia Specific";
  }

  revision 2023-03-02 {
    description
      "update lock/unlock error description";
    reference
      "Nokia Specific";
  }

  revision 2022-09-14 {
    description
      "update lock/unlock error discription";
    reference
      "BBN-101945";
  }

  revision 2022-02-21 {
    description
      "Added description for eqpt deviations";
    reference
      "BBN-65232";
  }

  revision 2020-03-18 {
    description
      "Efficient autogenerated hw deviations";
    reference
      "Nokia specific";
  }

  deviation "/hw:hardware/hw:component/hw:admin-state" {
    deviate add
    {
      must "current() = 'unlocked'
            or (current()/../hw:class = 'bbf-hwt:transceiver'
              and (
                  current() = 'locked'
                  or
                  current() = 'unlocked'
                  )
               )
           "
      {
        error-message "Given 'admin-state' value is not supported on this hardware component and system combination";
        description "Error occurs when hardware component does not support 'admin-state' locked or when given value is unknown/shutting-down.";
      }
    }
  }
  deviation "/hw:hardware/hw:component/hw:class" {
    deviate add {
      must "
        (current() = 'bbf-hwt:cage'
          and (
            (current()/../hw:parent-rel-pos <= 16 and (
                /hw:hardware/hw:component[hw:name = current()/../hw:parent]/hw:class = 'nokia-hwi:lt'
              )
            )
          )
        )
        or (current() = 'bbf-hwt:transceiver'
          and (
            (current()/../hw:parent-rel-pos <= 1 and (
                /hw:hardware/hw:component[hw:name = current()/../hw:parent]/hw:class = 'bbf-hwt:cage'
              )
            )
          )
        )
        or (current() = 'nokia-hwi:transceiver-link-gpon'
          and (
            (current()/../hw:parent-rel-pos <= 1 and (
                /hw:hardware/hw:component[hw:name = current()/../hw:parent]/hw:class = 'bbf-hwt:transceiver'
              )
            )
          )
        )
        or (current() = 'nokia-hwi:transceiver-link-ngpon'
          and (
            (current()/../hw:parent-rel-pos <= 1 and (
                /hw:hardware/hw:component[hw:name = current()/../hw:parent]/hw:class = 'bbf-hwt:transceiver'
              )
            )
          )
        )
        or (current() = 'nokia-hwi:transceiver-link-xgpon'
          and (
            (current()/../hw:parent-rel-pos <= 1 and (
                /hw:hardware/hw:component[hw:name = current()/../hw:parent]/hw:class = 'bbf-hwt:transceiver'
              )
            )
          )
        )
        or (current() = 'nokia-hwi:transceiver-link-twentyfivegspon'
          and (
            (current()/../hw:parent-rel-pos <= 1 and (
                /hw:hardware/hw:component[hw:name = current()/../hw:parent]/hw:class = 'bbf-hwt:transceiver'
              )
            )
          )
        )
        or (current() = 'nokia-hwi:slot-lt'
          and (
            (current()/../hw:parent-rel-pos <= 16 and (
                /hw:hardware/hw:component[hw:name = current()/../hw:parent]/hw:class = 'ianahw:chassis'
              )
            )
          )
        )
        or (current() = 'nokia-hwi:lt'
          and (
            (current()/../hw:parent-rel-pos <= 1 and (
                /hw:hardware/hw:component[hw:name = current()/../hw:parent]/hw:class = 'nokia-hwi:slot-lt'
              )
            )
          )
        )
        or (current() = 'nokia-hwi:backplane-port'
          and (
            (current()/../hw:parent-rel-pos <= 1 and (
                /hw:hardware/hw:component[hw:name = current()/../hw:parent]/hw:class = 'nokia-hwi:lt'
              )
            )
          )
        )
        or (current() = 'ianahw:chassis'
        )
      "
      {
        error-message "There is an inconsistency between the configured class, its parent class, and the 'parent-rel-pos' leaf of the component.";
        description "Configured relation between the component class, its parent class and the relative positon of the parent is not-valid,
        e.g. the parent class of the component transceiver must be cage and the parent relative position must be 1";
      }
    }
  }
}
