module nokia-ietf-interfaces-inexpressible-constraints-validator-gpon-xgs-dev {

  yang-version "1.1";
  namespace "http://www.nokia.com/Fixed-Networks/BBA/yang/"
            + "nokia-ietf-interfaces-inexpressible-constraints-validator-gpon-xgs-dev";

  prefix nokia-ietf-interfaces-inexpressible-constraints-validator-gpon-xgs-dev;

  import ietf-interfaces {
    prefix if;
  }
  
  organization
    "NOKIA";

  contact
    "Comments or questions about this Nokia YANG module should be
     directed to <mailto:isam.yang@nokia.com>.";

  description
    "The NOKIA common/nokia-ietf-interfaces-inexpressible-constraints-validator-gpon-xgs-dev
     YANG module supporting deviations on top of ietf-ssh-server standard.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2019, Nokia. All Rights Reserved.";

  revision 2024-04-24 {
    description
      "Initial revision.";
    reference
      "Nokia specific"; 
  }

  deviation "/if:interfaces/if:interface" {
    description
      "The error message 'The onu-id is not allowed to be modified.' will be displayed when the constraint is violated.";
    deviate add {}
  }
  
  deviation "/if:interfaces/if:interface" {
    description
      "The error message 'The channel pair line rate can be modified when channel-pair is admin-down.' will be displayed when the constraint is violated.";
    deviate add {}
  }
  
  deviation "/if:interfaces/if:interface" {
    description
      "The error message 'The meant-for-type-b-primary-role can't be modified to false or from false to true.' will be displayed when the constraint is violated.";
    deviate add {}
  }
  
  deviation "/if:interfaces/if:interface" {
    description
      "The error message 'The channel-partition-index should be unique under same channel-group.' will be displayed when the constraint is violated.";
    deviate add {}
  }
  
  deviation "/if:interfaces/if:interface" {
    description
      "The error message 'When channel-pair-type is NGPON2, wavelength-prof-ref should be unique under same channel-group.' will be displayed when the constraint is violated.";
    deviate add {}
  }
  
  deviation "/if:interfaces/if:interface" {
    description
      "The error message 'More than one inside-olt or outside-olt channel-termination refer to same channel-pair.' will be displayed when the constraint is violated.";
    deviate add {}
  }
  
  deviation "/if:interfaces/if:interface" {
    description
      "The error message 'For non-NGPON2 type, only one channel-pair is allowed in a channel-group.' will be displayed when the constraint is violated.";
    deviate add {}
  }
  
  deviation "/if:interfaces/if:interface" {
    description
      "The error message 'Only one kind of channel-pair-type is allowed in one channel-partition.' will be displayed when the constraint is violated.";
    deviate add {}
  }
  
  deviation "/if:interfaces/if:interface" {
    description
      "The error message 'Duplicate expected-serial-number under same channel-partition.' will be displayed when the constraint is violated.";
    deviate add {}
  }
  
  deviation "/if:interfaces/if:interface" {
    description
      "The error message 'The onu-id should be unique under same channel-group and same PON technology (GPON, XGSPON, etc.).' will be displayed when the constraint is violated.";
    deviate add {}
  }
  
  deviation "/if:interfaces/if:interface" {
    description
      "The error message 'The onu-name should be unique in all v-ani interfaces.' will be displayed when the constraint is violated.";
    deviate add {}
  }
  
  deviation "/if:interfaces/if:interface" {
    description
      "The error message 'Duplicate expected-registration-id under same channel-partition.' will be displayed when the constraint is violated.";
    deviate add {}
  }
  
  deviation "/if:interfaces/if:interface" {
    description
      "Other dependent xpaths where this rule applies are:
        '/bbf-xpongemtcont:xpongemtcont/bbf-xpongemtcont:tconts/bbf-xpongemtcont:tcont'
       The error message 'The alloc-id should be unique under same channel-group and same PON technology (GPON, XGSPON, etc.).' will be displayed when the constraint is violated.";
    deviate add {}
  }
  
  deviation "/if:interfaces/if:interface" {
    description
      "The error message 'There should be channel-termination available of this channel-pair.' will be displayed when the constraint is violated.";
    deviate add {}
  }
  
  deviation "/if:interfaces/if:interface" {
    description
      "The error message 'Must reference a channel-group.' will be displayed when the constraint is violated.";
    deviate add {}
  }
  
  deviation "/if:interfaces/if:interface" {
    description
      "The error message 'Must reference a channel-partition associated with the same channel-group this channel-pair is associated with.' will be displayed when the constraint is violated.";
    deviate add {}
  }
  
  deviation "/if:interfaces/if:interface" {
    description
      "The error message 'Must reference a channel-group.' will be displayed when the constraint is violated.";
    deviate add {}
  }
  
  deviation "/if:interfaces/if:interface" {
    description
      "The error message 'Must reference a channel-pair with the same PON type as the channel-termination.' will be displayed when the constraint is violated.";
    deviate add {}
  }
  
  deviation "/if:interfaces/if:interface" {
    description
      "The error message 'When channel-pair-type is NGPON2, channel-partition-index and system-id must be input.' will be displayed when the constraint is violated.";
    deviate add {}
  }
  
  deviation "/if:interfaces/if:interface" {
    description
      "The error message 'There should be channel-termination available of this channel-pair.' will be displayed when the constraint is violated.";
    deviate add {}
  }
  
  deviation "/if:interfaces/if:interface" {
    description
      "Other dependent xpaths where this rule applies are:
        '/bbf-xpongemtcont:xpongemtcont/bbf-xpongemtcont:gemports/bbf-xpongemtcont:gemport'
       The error message 'The gemport-id should be unique under same channel-group and same PON technology (GPON, XGSPON, etc.).' will be displayed when the constraint is violated.";
    deviate add {}
  }
  
  deviation "/if:interfaces/if:interface" {
    description
      "The error message 'Total number of v-ani interface on a channel-pair is limited.' will be displayed when the constraint is violated.";
    deviate add {}
  }
  
  deviation "/if:interfaces/if:interface" {
    description
      "Other dependent xpaths where this rule applies are:
        '/bbf-xpongemtcont:xpongemtcont/bbf-xpongemtcont:tconts/bbf-xpongemtcont:tcont'
       The error message 'Total number of tcont on a specific PON is limited.' will be displayed when the constraint is violated.";
    deviate add {}
  }
  
  deviation "/if:interfaces/if:interface" {
    description
      "Other dependent xpaths where this rule applies are:
        '/bbf-xpongemtcont:xpongemtcont/bbf-xpongemtcont:tconts/bbf-xpongemtcont:tcont'
        '/bbf-xpongemtcont:xpongemtcont/bbf-xpongemtcont:traffic-descriptor-profiles/bbf-xpongemtcont:traffic-descriptor-profile'
       The error message 'The channel-pair upstream bandwidth check error: ' will be displayed when the constraint is violated.";
    deviate add {}
  }
  
  deviation "/if:interfaces/if:interface" {
    description
      "The error message 'This port-layer-if has already been used by another channel-termination.' will be displayed when the constraint is violated.";
    deviate add {}
  }
  
  deviation "/if:interfaces/if:interface" {
    description
      "The error message 'Total number of olt-v-enet interface with counter flag all-available is limited.' will be displayed when the constraint is violated.";
    deviate add {}
  }
  
  deviation "/if:interfaces/if:interface" {
    description
      "Other dependent xpaths where this rule applies are:
        '/bbf-xpongemtcont:xpongemtcont/bbf-xpongemtcont:tconts/bbf-xpongemtcont:tcont'
       The error message 'The alloc-id is out of range. For GPON: The alloc-id range is 256~1023. For others: The alloc-id range is 1024~16383.' will be displayed when the constraint is violated.";
    deviate add {}
  }
  
  deviation "/if:interfaces/if:interface" {
    description
      "Other dependent xpaths where this rule applies are:
        '/bbf-xpongemtcont:xpongemtcont/bbf-xpongemtcont:gemports/bbf-xpongemtcont:gemport'
       The error message 'The gemport-id is out of range. For GPON: The gemport-id range is 256~1915. For 50GPON: The gemport-id range is 1020~6644. For others: The gemport-id range is 1024~6648.
RMTDBG gemport-id range is 1916~2044 for GPON, and 64506~65526 for others.' will be displayed when the constraint is violated.";
    deviate add {}
  }
  
  deviation "/if:interfaces/if:interface" {
    description
      "The error message 'Must reference a channel-partition.' will be displayed when the constraint is violated.";
    deviate add {}
  }
  
  deviation "/if:interfaces/if:interface" {
    description
      "The error message 'Must reference a channel-pair and the channel-pair should belong to same channel-partition, The preferred-channel-pair can't be the same as the protection-channel-pair.' will be displayed when the constraint is violated.";
    deviate add {}
  }
  
  deviation "/if:interfaces/if:interface" {
    description
      "The error message 'Must reference a channel-pair and the channel-pair should belong to same channel-partition. The protection-channel-pair can't be the same as the preferred-channel-pair.' will be displayed when the constraint is violated.";
    deviate add {}
  }
  
  deviation "/if:interfaces/if:interface" {
    description
      "The error message 'If both preferred-channel-pair and protection-channel-pair are configured, the preferred-channel-pair and protection-channel-pair must both be NGPON2 type.' will be displayed when the constraint is violated.";
    deviate add {}
  }
  
  deviation "/if:interfaces/if:interface" {
    description
      "The error message 'For NGPON2: The onu-id range is 0~255. For others: The onu-id range is 0~127.' will be displayed when the constraint is violated.";
    deviate add {}
  }
  
  deviation "/if:interfaces/if:interface" {
    description
      "The error message 'For GPON case, only value 1.25G is supported. For XGSPON case, it can be 10G or 2.5G. For XGPON case, it can be 2.5G. For NGPON2 case, it can be 10G. For 25GSPON case, it can be 10G and 25G. For 50GPON case, it can be 25G and 50G.' will be displayed when the constraint is violated.";
    deviate add {}
  }
  
  deviation "/if:interfaces/if:interface" {
    description
      "The error message 'Must reference a v-ani.' will be displayed when the constraint is violated.";
    deviate add {}
  }
  
  deviation "/if:interfaces/if:interface" {
    description
      "The error message 'Invalid channel-termination configured.' will be displayed when the constraint is violated.";
    deviate add {}
  }
  
  deviation "/if:interfaces/if:interface" {
    description
      "The error message 'The host-id-of-primary-side should be configured only in type-b enabled case.' will be displayed when the constraint is violated.";
    deviate add {}
  }
  
  deviation "/if:interfaces/if:interface" {
    description
      "The error message 'Only best-effort is supported for channel-termination interface.' will be displayed when the constraint is violated.";
    deviate add {}
  }
  
  deviation "/if:interfaces/if:interface" {
    description
      "The error message 'The v-ethernet-id in olt-v-enet interface is not unique.' will be displayed when the constraint is violated.";
    deviate add {}
  }
  
  deviation "/if:interfaces/if:interface" {
    description
      "Other dependent xpaths where this rule applies are:
        '/sys:system/nokia-sdan-vmac-host-id-aug:host-id/nokia-sdan-vmac-host-id-aug:host-id'
       The error message 'The host-id-of-primary-side should not be same as host-id configured at system.' will be displayed when the constraint is violated.";
    deviate add {}
  }
  
  deviation "/if:interfaces/if:interface" {
    description
      "The error message 'For XGSPON: closest-onu-distance can only be 0, 20 or 40. For XGPON/25GSPON/50GPON: closest-onu-distance can only be 0 or 20.' will be displayed when the constraint is violated.";
    deviate add {}
  }
  
  deviation "/if:interfaces/if:interface" {
    description
      "The error message 'For XGPON/50GPON: maximum-differential-xpon-distance can only be 20.' will be displayed when the constraint is violated.";
    deviate add {}
  }
  
  deviation "/if:interfaces/if:interface" {
    description
      "The error message 'The authentication-method is not allowed to be modified from/to loid.' will be displayed when the constraint is violated.";
    deviate add {}
  }
  
  deviation "/if:interfaces/if:interface" {
    description
      "The error message 'The authentication-method is not allowed to be modified when sma-required of any descending v-ani is enabled.' will be displayed when the constraint is violated.";
    deviate add {}
  }
  
  deviation "/if:interfaces/if:interface" {
    description
      "The error message 'The expected-loid should be unique inside one channel-partition.' will be displayed when the constraint is violated.";
    deviate add {}
  }
  
  deviation "/if:interfaces/if:interface" {
    description
      "The error message 'The expected-loid shouldn't be set to a v-ani when authentication method is as-per-v-ani-expected.' will be displayed when the constraint is violated.";
    deviate add {}
  }
  
  deviation "/if:interfaces/if:interface" {
    description
      "The error message 'The authentication-method can't be set to loid if type-b feature is enabled on one of its channel-termination.' will be displayed when the constraint is violated.";
    deviate add {}
  }
  
  deviation "/if:interfaces/if:interface" {
    description
      "The error message 'The us-omci-granting can't be set to relaxed if type-b feature is enabled on one of its channel-termination.' will be displayed when the constraint is violated.";
    deviate add {}
  }
  
  deviation "/if:interfaces/if:interface" {
    description
      "The error message 'The sma-required shouldn't be set to a v-ani when authentication method is loid/registration-id, or per-vani with registration-id configured, or in type-b mode, or in gpon technology.' will be displayed when the constraint is violated.";
    deviate add {}
  }
  
}
