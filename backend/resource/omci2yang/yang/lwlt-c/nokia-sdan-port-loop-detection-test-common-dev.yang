module nokia-sdan-port-loop-detection-test-common-dev {
  yang-version 1.1;
  namespace "http://www.nokia.com/Fixed-Networks/BBA/yang/"
           + "nokia-sdan-port-loop-detection-test-common-dev";
  prefix pld-dev;

  import nokia-sdan-port-loop-detection-test {
    prefix nokia-port-loop;
  }

  import ietf-interfaces {
    prefix if;
  }

  import bbf-interface-usage {
    prefix bbf-if-usg;
  }

  import iana-if-type {
    prefix ianaift;
  }

  import bbf-if-type {
    prefix bbfift;
  }

  organization
    "Nokia";

  contact
    "Comments or questions about this Nokia YANG module should be
     directed to <mailto:isam.yang@nokia.com>.";

  description
    "This module contains a collection of YANG definitions for
     supporting Nokia specific requirements as applicable to its
     access network equipment.

     Specifically, this module defines configuration and operational
     state data for ethernet loop detection.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

  revision 2026-06-12 {
    description
      "Initial revision.";
    reference
      "Nokia specific.";
  }

  deviation "/nokia-port-loop:port-loop-detection-test/nokia-port-loop:loop-test/"+
            "nokia-port-loop:test-injection-point/nokia-port-loop:at-forwarder-scope/"+
            "nokia-port-loop:forwarders-under-test/nokia-port-loop:applicable-interfaces/"+
            "nokia-port-loop:matching-interface-usage" {
    deviate add {
      must ". = 'user-port'" {
        error-message
          "Only 'user-port' is supported for matching-interface-usage.";
      }
    }
  }

  deviation "/nokia-port-loop:port-loop-detection-test/nokia-port-loop:loop-test/"+
            "nokia-port-loop:test-injection-point/nokia-port-loop:at-forwarder-scope/"+
            "nokia-port-loop:forwarders-under-test/nokia-port-loop:applicable-interfaces/"+
            "nokia-port-loop:lowerlayer-interface-type" {
    deviate add {
      must "current() = 'bbfift:vlan-sub-interface'" {
        error-message
          "Only 'vlan-sub-interface' is supported for lowerlayer-interface-type.";
      }
    }
  }

  deviation "/nokia-port-loop:port-loop-detection-test/nokia-port-loop:loop-test/"+
            "nokia-port-loop:auto-recovery-time" {
    deviate add {
      must ". >= 60 and . <= 3600" {
        error-message
          "auto-recovery-time must be between 60 seconds and 3600 seconds (1 hour).";
      }
      must "../nokia-port-loop:loop-detection-action = 'nokia-port-loop:no-action'" {
        error-message
          "auto-recovery-time is only applicable when loop-detection-action is no-action.";
      }
    }
  }

  deviation "/nokia-port-loop:port-loop-detection-test/nokia-port-loop:loop-test/"+
            "nokia-port-loop:test-injection-point/nokia-port-loop:at-eth-itf-scope/"+
            "nokia-port-loop:interfaces/nokia-port-loop:name" {
    description
      "Port loop detection at ethernet interface scope can be enabled only on uplink port.";
    deviate add {
      must "(/if:interfaces/if:interface[if:name = current()]/if:type"+
           " = 'ianaift:ethernetCsmacd') and (/if:interfaces/if:interface"+
           "[if:name = current()]/bbf-if-usg:interface-usage/bbf-if-usg:"+
           "interface-usage = 'network-port') and (current() != 'BP_Eth')" {
        error-message
          "Ethernet Loop detection is supported only on Uplink ethernet port.";
      }
    }
  }

  deviation "/nokia-port-loop:port-loop-detection-test/nokia-port-loop:loop-test/"+
            "nokia-port-loop:statistics/nokia-port-loop:interfaces/nokia-port-loop:name" {
    description
      "Port loop detection statistics are reported only for uplink ethernet
       ports configured under at-eth-itf-scope.";
    deviate add {
      must "(/if:interfaces/if:interface[if:name = current()]/if:type"+
           " = 'ianaift:ethernetCsmacd') and (/if:interfaces/if:interface"+
           "[if:name = current()]/bbf-if-usg:interface-usage/bbf-if-usg:"+
           "interface-usage = 'network-port') and (current() != 'BP_Eth')" {
        error-message
          "Ethernet Loop detection is supported only on Uplink ethernet port.";
      }
    }
  }

  deviation "/nokia-port-loop:port-loop-detection-test/nokia-port-loop:loop-test/"+
            "nokia-port-loop:test-injection-point/nokia-port-loop:at-eth-itf-scope/"+
            "nokia-port-loop:interfaces/nokia-port-loop:vlan-list" {
    description
      "Only one VLAN list is supported.";
    deviate add {
      max-elements 1;
    }
  }

  deviation "/nokia-port-loop:port-loop-detection-test/nokia-port-loop:loop-test/"+
            "nokia-port-loop:test-injection-point/nokia-port-loop:at-eth-itf-scope/"+
            "nokia-port-loop:interfaces/nokia-port-loop:vlan-list/"+
            "nokia-port-loop:vlan-tag/nokia-port-loop:index" {
    description
      "Index 0 represents the outer VLAN, and Index 1 represents the inner VLAN. "
    + "However, at present, only Index 0 (outer VLAN) is supported.";
    deviate replace {
      type uint8 {
        range "0";
      }
    }
  }

  deviation "/nokia-port-loop:port-loop-detection-test/nokia-port-loop:loop-test/"+
            "nokia-port-loop:test-injection-point/nokia-port-loop:at-eth-itf-scope/"+
            "nokia-port-loop:interfaces/nokia-port-loop:vlan-list/"+
            "nokia-port-loop:vlan-tag/nokia-port-loop:pbit" {
    description
      "Not supported in current feature scope.";
    deviate not-supported;
  }

  deviation "/nokia-port-loop:port-loop-detection-test/nokia-port-loop:loop-test/"+
            "nokia-port-loop:test-injection-point/nokia-port-loop:at-eth-itf-scope/"+
            "nokia-port-loop:interfaces/nokia-port-loop:vlan-list/"+
            "nokia-port-loop:vlan-tag/nokia-port-loop:dei" {
    description
      "Not supported in current feature scope.";
    deviate not-supported;
  }
}
