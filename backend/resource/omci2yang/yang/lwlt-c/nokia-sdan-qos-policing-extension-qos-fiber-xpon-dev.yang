module nokia-sdan-qos-policing-extension-qos-fiber-xpon-dev {

  namespace
    "http://www.nokia.com/Fixed-Networks/BBA/yang/nokia-sdan-qos-policing-extension-qos-fiber-xpon-dev";

  prefix  nokia-sdan-qos-policing-extension-qos-fiber-xpon-dev;

  import nokia-sdan-qos-policing-extension {
    prefix nokia-qos-plc-ext;
  }

  import bbf-qos-policing {
    prefix bbf-qos-plc;
  }

  organization
    "Nokia";

  contact
    "isam.yang@nokia.com";

  description
    "This module contains a collection of YANG deviations on top
     of standard for supporting BBF/nokia-sdan-qos-policing-extension YANG module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2017-2018, Nokia. All Rights Reserved.";

  /* revision */
  revision 2024-05-14 {
    description
      "Revert the policing pre-handling-profile check modifications.";
    reference
      "Nokia specific";
  }

  /* revision */
  revision 2024-03-06 {
    description
      "Update for BBN-117456.";
    reference
      "Nokia specific";
  }

  revision 2022-12-20 {
    description
      "Initial revision.";
    reference
      "Nokia specific";
  }

  deviation "/nokia-qos-plc-ext:policing-action-profiles/nokia-qos-plc-ext:action-profile/nokia-qos-plc-ext:action/nokia-qos-plc-ext:action-cfg-params/nokia-qos-plc-ext:assign-metadata/nokia-qos-plc-ext:pbit-marking-list/nokia-qos-plc-ext:index"
  {
    deviate add {
      must "current() <= 1"
      {
        error-message "pbit-marking index can't exceed 1.";
      }
    }
  }

  deviation "/nokia-qos-plc-ext:policing-action-profiles/nokia-qos-plc-ext:action-profile/nokia-qos-plc-ext:action/nokia-qos-plc-ext:action-cfg-params/nokia-qos-plc-ext:assign-metadata/nokia-qos-plc-ext:dei-marking-list/nokia-qos-plc-ext:index"
  {
    deviate add {
      must "current() <= 1"
      {
        error-message "dei-marking index can't exceed 1.";
      }
    }
  }

  deviation "/nokia-qos-plc-ext:policing-action-profiles/nokia-qos-plc-ext:action-profile/nokia-qos-plc-ext:action/nokia-qos-plc-ext:action-cfg-params/nokia-qos-plc-ext:assign-metadata/nokia-qos-plc-ext:dei-marking-list"
  {
    /* BBN-114329 D-7 */
    deviate add {
       must "(../nokia-qos-plc-ext:flow-color != 'green')"
       {
            error-message "In qos policing action-profile, if the action is dei-marking-list, the flow-color can not be green.";
       }
    }
  }

  /* BBN-114329 D-73 */
  deviation "/nokia-qos-plc-ext:policing-pre-handling-profiles/nokia-qos-plc-ext:pre-handling-profile"
  {
    deviate add {
      must "(count(nokia-qos-plc-ext:pre-handling-entry/nokia-qos-plc-ext:match-params/nokia-qos-plc-ext:vlans/nokia-qos-plc-ext:tag/nokia-qos-plc-ext:in-pbit-list) = 0
        or count(nokia-qos-plc-ext:pre-handling-entry/nokia-qos-plc-ext:match-params/nokia-qos-plc-ext:vlans/nokia-qos-plc-ext:tag/nokia-qos-plc-ext:in-pbit-list) = count(nokia-qos-plc-ext:pre-handling-entry))
      and (count(nokia-qos-plc-ext:pre-handling-entry/nokia-qos-plc-ext:match-params/nokia-qos-plc-ext:vlans/nokia-qos-plc-ext:tag/nokia-qos-plc-ext:in-dei) = 0
        or count(nokia-qos-plc-ext:pre-handling-entry/nokia-qos-plc-ext:match-params/nokia-qos-plc-ext:vlans/nokia-qos-plc-ext:tag/nokia-qos-plc-ext:in-dei) = count(nokia-qos-plc-ext:pre-handling-entry))
      and (count(nokia-qos-plc-ext:pre-handling-entry/nokia-qos-plc-ext:match-params/nokia-qos-plc-ext:pbit-marking-list) = 0
        or count(nokia-qos-plc-ext:pre-handling-entry/nokia-qos-plc-ext:match-params/nokia-qos-plc-ext:pbit-marking-list) = count(nokia-qos-plc-ext:pre-handling-entry))
      and (count(nokia-qos-plc-ext:pre-handling-entry/nokia-qos-plc-ext:match-params/nokia-qos-plc-ext:dei-marking-list) = 0
        or count(nokia-qos-plc-ext:pre-handling-entry/nokia-qos-plc-ext:match-params/nokia-qos-plc-ext:dei-marking-list) = count(nokia-qos-plc-ext:pre-handling-entry))
      and (count(nokia-qos-plc-ext:pre-handling-entry/nokia-qos-plc-ext:flow-color) = 0
        or count(nokia-qos-plc-ext:pre-handling-entry/nokia-qos-plc-ext:flow-color) = count(nokia-qos-plc-ext:pre-handling-entry))"
      {
        error-message "The filters and actions of all pre-handling-entry in same pre-handling-profile must be homogeneous.";
      }

       /* BBN-114329 D-N17 */
      must "( not(boolean(nokia-qos-plc-ext:pre-handling-entry))
              or 
              (boolean(nokia-qos-plc-ext:pre-handling-entry) and boolean(nokia-qos-plc-ext:pre-handling-entry/nokia-qos-plc-ext:flow-color) and ( boolean(nokia-qos-plc-ext:pre-handling-entry/nokia-qos-plc-ext:match-params/nokia-qos-plc-ext:pbit-marking-list) or boolean(nokia-qos-plc-ext:pre-handling-entry/nokia-qos-plc-ext:match-params/nokia-qos-plc-ext:dei-marking-list) or boolean(nokia-qos-plc-ext:pre-handling-entry/nokia-qos-plc-ext:match-params/nokia-qos-plc-ext:vlans/nokia-qos-plc-ext:tag)))
            )"
      {
        error-message "For policing-pre-handling profile , there shouldn't be empty entry";
      }

      must "( ( boolean(nokia-qos-plc-ext:pre-handling-entry/nokia-qos-plc-ext:match-params/nokia-qos-plc-ext:pbit-marking-list) 
                and nokia-qos-plc-ext:pre-handling-entry/nokia-qos-plc-ext:match-params/nokia-qos-plc-ext:pbit-marking-list/nokia-qos-plc-ext:index <= 1)
             or not(boolean(nokia-qos-plc-ext:pre-handling-entry/nokia-qos-plc-ext:match-params/nokia-qos-plc-ext:pbit-marking-list))
            )"
      {
        error-message "pbit-marking index can't exceed 1.";
      }

      must "( ( boolean(nokia-qos-plc-ext:pre-handling-entry/nokia-qos-plc-ext:match-params/nokia-qos-plc-ext:dei-marking-list)
                and nokia-qos-plc-ext:pre-handling-entry/nokia-qos-plc-ext:match-params/nokia-qos-plc-ext:dei-marking-list/nokia-qos-plc-ext:index <= 1)
             or not(boolean(nokia-qos-plc-ext:pre-handling-entry/nokia-qos-plc-ext:match-params/nokia-qos-plc-ext:dei-marking-list))
            )"
      {
        error-message "dei-marking index can't exceed 1.";
      }

      must "( count(nokia-qos-plc-ext:pre-handling-entry/nokia-qos-plc-ext:match-params/nokia-qos-plc-ext:vlans/nokia-qos-plc-ext:tag[nokia-qos-plc-ext:index = 0]) = count(nokia-qos-plc-ext:pre-handling-entry)
        or
              count(nokia-qos-plc-ext:pre-handling-entry/nokia-qos-plc-ext:match-params/nokia-qos-plc-ext:vlans/nokia-qos-plc-ext:tag[nokia-qos-plc-ext:index = 1]) = count(nokia-qos-plc-ext:pre-handling-entry)
        or
              count(nokia-qos-plc-ext:pre-handling-entry/nokia-qos-plc-ext:match-params/nokia-qos-plc-ext:pbit-marking-list[nokia-qos-plc-ext:index = 0]) = count(nokia-qos-plc-ext:pre-handling-entry)
        or
              count(nokia-qos-plc-ext:pre-handling-entry/nokia-qos-plc-ext:match-params/nokia-qos-plc-ext:pbit-marking-list[nokia-qos-plc-ext:index = 1]) = count(nokia-qos-plc-ext:pre-handling-entry)
        or
              count(nokia-qos-plc-ext:pre-handling-entry/nokia-qos-plc-ext:match-params/nokia-qos-plc-ext:dei-marking-list[nokia-qos-plc-ext:index = 0]) = count(nokia-qos-plc-ext:pre-handling-entry)
        or
              count(nokia-qos-plc-ext:pre-handling-entry/nokia-qos-plc-ext:match-params/nokia-qos-plc-ext:dei-marking-list[nokia-qos-plc-ext:index = 1]) = count(nokia-qos-plc-ext:pre-handling-entry)
       )"
      {
        error-message "All entries in the pre-handling-profile must use the same tag index.";
      }
    }
  }

  /* BBN-114329 D-24 */
  deviation "/bbf-qos-plc:policing-profiles/bbf-qos-plc:policing-profile/nokia-qos-plc-ext:policing-pre-handling-profile"
  {
    deviate add {
      must "(../bbf-qos-plc:two-rate-three-color-marker-mef)"
      {
        error-message "Only 3 types of two-rate-three-color-marker-mef/two-rate-three-color-marker-with-cos/two-rate-three-color-marker-mef-with-cos policing profile can reference a pre-handling-profile.";
      }
    }
  }
}
