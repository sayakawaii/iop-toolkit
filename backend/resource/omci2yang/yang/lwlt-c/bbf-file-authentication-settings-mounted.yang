submodule bbf-file-authentication-settings-mounted {
  yang-version 1.1;
  belongs-to bbf-sip-voip-mounted  {
    prefix bbf-sip-voip-mounted;
  }

  import bbf-yang-types {
    prefix bbf-yang;
  }

  import tailf-common {
    prefix tailf;
  }

  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains a collection of YANG definitions for
     managing authentication profiles.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2021-07-06 {
    description
      "Add md5-digest-authentication in authentication-scheme type";
    reference
      "";
  }  
  revision 2020-03-06 {
    description
      "Initial revision.
       * Approval Date:    see revision date above.
       * Publication Date: 2020-03-06.";
    reference
      " ";
  }

  grouping file-authentication-settings {    
    leaf authentication-scheme {
	  type enumeration {
	    enum basic-authentication {
		  value 1;
		  description
		    "Basic authentication required for file 
			 transfer.";
		} 
		enum basic-ssh-authentication {
		  value 2;
		  description
		    "Basic authentication for SFTP 
			 secured file transfer.";
		} 
        enum md5-digest-authentication {
          value 3;
          description
            "MD5 Digest authentication for file transfer.";
        }
	  }
	  default basic-authentication;
	  description
		"Authentication validation scheme for file transfer.";
	}   
	leaf user-name {
	  type bbf-yang:name-string;		
	  description
	   "The user name for file transfer to be validated.";
    }
    leaf password {
    when "../bbf-sip-voip-mounted:authentication-scheme !="
       + "'basic-ssh-authentication'";
      type tailf:aes-cfb-128-encrypted-string;
      description
        "The authentication password for file transfer.";
    }
    leaf realm {
    when "../bbf-sip-voip-mounted:authentication-scheme ="
       + "'md5-digest-authentication'";
      type bbf-yang:name-string;
      description
        "This string attribute specifies the realm used in MD5 digest authentication.";
    }
	leaf ssh-public-key {
	when "../bbf-sip-voip-mounted:authentication-scheme = "
		+ "'basic-ssh-authentication'";
	 type string;		
	 description
		"The authentication public SSH key for secured file 
		 transfer";
	}	
  } 
}
