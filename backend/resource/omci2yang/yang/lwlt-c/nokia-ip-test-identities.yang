module nokia-ip-test-identities {
  yang-version 1.1;

  namespace "http://www.nokia.com/Fixed-Networks/BBA/yang/"
           + "nokia-ip-test-identities";

  prefix nokia-ip-test-identities;


  organization
    "Nokia";

  contact
    "Comments or questions about this Nokia YANG module should be
     directed to <mailto:isam.mibsupport@nokia.com>.";

  description
    "This module contains a collection of YANG definitions for
     supporting Nokia specific requirements as applicable to its
     access network equipment.

     Specifically, this module contains a collection of YANG
     definitions for testing IP connectivity.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";


  revision 2026-06-22 {
    description
      "Add traceroute result identity.";
    reference
      "Nokia specific EPIC BBN-326129";
  }

  revision 2021-07-30 {
    description
      "Initial revision.
       * Approval Date:    see revision date above.
       * Publication Date: yyyy-mm-dd.";
    reference
      "Nokia specific";
  }

  identity ping-result-base {
    description
      "This identity is used to denote the possible result of an IP
       ping.";
  }
  identity success {
    base ping-result-base;
    description
      "This identity is used to denote a successful ping.";
  }
  identity unexpected-icmp-received {
    base ping-result-base;
    description
      "This identity is used to denote that there was an unexpected
       ICMP message received following the ping request.";
  }
  identity no-response {
    base ping-result-base;
    description
      "This identity is used to denote that there was no ICMP message
       received following the ping request.";
  }
  identity unresolved-domain-name {
    base ping-result-base;
    description
      "This identity is used to denote that the target domain name
       could not be resolved.";
  }

  identity traceroute-result-base {
    description
      "This identity is used to denote the possible result of an IP
       traceroute.";
  }
  identity traceroute-complete {
    base traceroute-result-base;
    description
      "This identity is used to denote a traceroute that completed
       successfully, reaching the destination.";
  }
  identity traceroute-max-hops-exceeded {
    base traceroute-result-base;
    description
      "This identity is used to denote that the traceroute did not
       reach the destination within the configured maximum number
       of hops.";
  }
  identity traceroute-no-response {
    base traceroute-result-base;
    description
      "This identity is used to denote that there was no response
       received for the traceroute request (timed out).";
  }
  identity traceroute-unresolved-domain-name {
    base traceroute-result-base;
    description
      "This identity is used to denote that the target domain name
       could not be resolved.";
  }
  identity traceroute-unexpected-response {
    base traceroute-result-base;
    description
      "This identity is used to denote that an unexpected ICMP
       response was received.";
  }
}
