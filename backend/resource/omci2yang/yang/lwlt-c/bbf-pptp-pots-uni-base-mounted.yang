submodule bbf-pptp-pots-uni-base-mounted {
  yang-version 1.1;
  belongs-to bbf-sip-voip-mounted  {
    prefix bbf-sip-voip-mounted;
  }

  import ietf-interfaces-mounted {
    prefix if-mounted;
  }
  
  import iana-if-type-mounted {
    prefix ianaift-mounted;
  } 
  
  import iana-hardware {
    prefix ianahw;
  }
  
  import bbf-fiber-onu-emulated-mount {
     prefix onu;
  }

  import nokia-template-common {
    prefix template-common;
  }  
    
  import ietf-hardware-mounted {
    prefix hw-mounted;
  }

  
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains a collection of YANG definitions for
     the Physical Path Termination Point uni (pptp pots uni).
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2020-03-06 {
    description
      "Initial revision.
       * Approval Date:    see revision date above.
       * Publication Date: 2020-03-06.";
    reference
      " ";
  }
  
  feature alarm-control {
	description
      "Indicates support for Alarm Control.";
	reference
		"ITU-T M.3100";
  }

  feature rings {
	description
	  "Indicates that the ring patterns are
	   explicitly configured by the operator or
	   pre-populated in a downloable file.";
  }

  feature ringtone-files {
	description
	  "Indicates that the tone and ring patterns are
	   pre-populated in a downloable file.";
  }
  
  feature tones {
    description
	  "Indicates that the tone patterns are
	   explicitly configured by the operator or
	   pre-populated in a downloable file.";
  }
	
  feature clip-data-mode {
    description
     "Indicates that the CLIP data mode is
	  explicitly configured by the operator or
	  pre-populated in a downloable file.";
  }
  
  /* typedef hardware-ref {
    type leafref {
      path "/hw:hardware/hw:component/hw:name";
    }
    description
      "Used to reference to a port component.";
  } */
// BBOG
//  typedef port-layer-if-ref {
//    type leafref {
//	  path "/if:interfaces/if:interface/port-layer-if";
//    }
//    description
//      "Used to reference to a port component. The port
//	   component must be a POTS port.";
//  }


 augment '/onu:onus/onu:onu/onu:root' {
  when "derived-from-or-self(../onu:usage, 'template-common:node-actual-usage') or "
       + "derived-from-or-self(../onu:usage, 'template-common:node-template-usage')" {
     description
       "it should be a node-actual-usage or node-template-usage ONU";
  } 	  
  container pots-profiles {
    description 
	  "The Yang model for the physical voice interface";
	container tone-pattern-profiles {
          if-feature tones;
	  description
	    "Tone pattern profiles.";
	}
	container ringing-pattern-profiles {
	  if-feature rings;
	  description
	    "Ringing pattern profiles.";
	}
	container file-profiles {
	  if-feature ringtone-files;
	  description
	    "File profiles for tones and ringing configuration.";
        }
	container pots-uni-characteristics-profiles {
	  description
	    "Pots uni characteristics configuration.";
        }
	container clip-data-mode-profiles {
	  if-feature clip-data-mode; 
	  description
	    "Clip data mode configuration.";
	}
   } 
 }

  augment "/onu:onus/onu:onu/onu:root/if-mounted:interfaces/if-mounted:interface" {   	
    when "if-mounted:type = 'ianaift-mounted:voiceFXS'" {
      description
        "Only applicable when the interface type is
		 Voice FXS"; 
    }
    description
	  "Data nodes for the configuration of Voice lines.";
    container phys-voice-itf {
	presence
            "If present, it indicates that the interface is able to 
	     operate by means of the integrated SIP VoIP service.";
	description
	    "The Yang model for the Physical voice interface.";
	  leaf port-layer-if {
          if-feature hw-mounted:hardware-config; //yanglint
          /* type hardware-ref; */
          type leafref {
             path "../../../../hw-mounted:hardware/hw-mounted:component/hw-mounted:name";
         }	   
	     must "derived-from-or-self("
               + "../../../../hw-mounted:hardware/hw-mounted:component[hw-mounted:name = current()]"
               + "/hw-mounted:class,'ianahw:port')" {
		/* new BBF identity type pots-port? */  
		  error-message
              "Referenced component is or is derived from class 'port'.";      
	    }
	    mandatory true;
	    description
                 "References the physical POTS port.";
	  }
    container pptp-pots-uni; 
    }
  }

  augment "/onu:onus/onu:onu/onu:root/if-mounted:interfaces-state/if-mounted:interface" {   	
    when "if-mounted:type = 'ianaift-mounted:voiceFXS'" {
      description
        "Only applicable when the interface type is
		 Voice FXS"; 
    }
    description
	  "Data nodes for the configuration of Voice lines.";	
// BBOG: do we need that extra container?
    container phys-voice-itf {
      container pptp-pots-uni;
    }
  }
}
