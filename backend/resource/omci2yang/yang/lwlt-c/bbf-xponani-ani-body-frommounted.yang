submodule bbf-xponani-ani-body-frommounted {
  yang-version 1.1;
  belongs-to bbf-xponani-frommounted  {
    prefix bbf-xponani-frommounted;
  }

  import ietf-interfaces-frommounted {
    prefix if-frommounted;
  }
  import bbf-fiber-onu-emulated-mount {
     prefix onu;
  }
  import nokia-yang-types {
    prefix nok-typ;
  }
  
  include bbf-xponani-base-frommounted;

  organization
    "Broadband Forum <https://www.broadband-forum.org>
     Fiber Access Networks Work Area";
  contact
    "Comments or questions about this Broadband Forum YANG module
     should be directed to <mailto:info@broadband-forum.org>.

     Editor:      Joey Boyd, ADTRAN

     Editor:      Igor Ternovsky, Broadcom

     Editor:      Robert Peschi, Nokia

     WA Director: Marta Seda, Calix

     WA Director: Samuel Chen, Broadcom";
  description
    "This submodule contains data related to the actual ONU devices.
     Each ONU device is 1:1 associated to its unique Access Network
     Interface (ANI).

     Copyright (c) 2018-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i2; see
     the TR itself for full legal notices.";

  revision 2025-12-09 {
    description
      "add traffic-class in fromroot";
    reference
      "Nokia Specific.";
  }
  revision 2020-10-13 {
    description
      "Issue 2.
       * Approval Date:    2020-10-13.
       * Publication Date: 2020-10-13.";
    reference
      "TR-385i2: ITU-T PON YANG Modules
               <https://www.broadband-forum.org/technical/download/
                        TR-385_Issue-2.pdf>";
  }
  revision 2019-02-25 {
    description
      "Initial revision.
       * Approval Date:    2019-02-25.
       * Publication Date: 2019-02-25.";
    reference
      "TR-385: ITU-T PON YANG Modules
               <https://www.broadband-forum.org/technical/download/
                        TR-385.pdf>";
  }

  grouping ani-config-data {
    description
      "Configuration data intended for the Optical Network Unit (ONU)
       physical device. This data is brought to the ONU, when present,
       for instance via the Physical Layer Operations, Administrations
       and Maintenance (PLOAM) channel or using ONU Management and
       Control Interface (OMCI) on the Management G-PON Encapsulation
       Method (GEM) port.";
    leaf management-gemport-id {
      type uint32;
      description
        "This leaf is only relevant to GPON ONUs; it is ignored for
         non-GPON ONUs. In contrast with other xPON technologies, in
         the case of G-PON, there is no requirement that the ITU-T TC
         ID of the management G-PON Encapsulation Method (GEM) port
         for the Optical Network Unit (ONU) is numerically equal to
         the ONU-ID. This leaf provides the capability to specify
         value for the management GEM port ID.

         If this leaf is not configured the management GEM port
         ID must be numerically equal to the ONU-ID.";
      reference
        "Refer to 'OMCC Port-ID' in
         ITU-T G.984.3 clause 5.5.5
         ITU-T G.987.3 clause 6.4.4
         ITU-T G.989.3, clause 6.1.5.8
         ITU-T G.9807.1 clause C.6.1.5.8";
    }
  }


  grouping onu-multicast-gemports-config-data {
    description
      "The config data of multicast GEM port(s), known by the ONU.
       Multicast GEM ports can be used for multicast or broadcast.";
    list multicast-gemport {
      key "name";
      leaf name {
        type nok-typ:nokia-string-ascii100;
        description
      "The name of the multicast GEM port";
      }
 
    leaf mc-gemport-id {
      type uint32;
      description
          "ID of MC GEM port. When configured this is the value which 
           must actually be used between the OLT device and ONU
           device for this MC GEM port. For G-PON the value should
           be in [0..4095] and not conflicting with the 
           management-gemport-id, for XG-PON it should be
           in [1023..65534] and for XGS-PON and NG-PON2 it should 
           be in [1021..65534]. The ID of a MC GEM port may not conflict
           with the ID of a UNI cast GEM port";
      reference
        "ITU-T G.984.3 clause 5.5.5
         ITU-T G.987.3 clause 6.4.4
         ITU-T G.9807.1 clause C.6.1.5.8
         ITU-T G.989.3 clause 6.1.5.8";
    }

    leaf interface {
      type string;
      description
        "The vENET associated with this MC GEM port.";
    }

    leaf traffic-class {
      type uint8 {
        range "0..7";
    }
    description
      "Traffic class value.";
    }
    leaf is-broadcast {
     type boolean;
     description
       "If true, this multicast GEM port is used for broadcast traffic.";
    }
    description
      "List of multicast GEM ports.";
  }
 }  

  augment "/onu:onus/onu:onu/onu:fromroot/if-frommounted:interfaces/if-frommounted:interface/bbf-xponani-frommounted:ani" {
    description
      "Configuration of an xPON Access Network Interface (ANI), i.e.
       an Optical Network Unit (ONU) device.";
    uses ani-config-data;
    uses onu-multicast-gemports-config-data;
  }

}
