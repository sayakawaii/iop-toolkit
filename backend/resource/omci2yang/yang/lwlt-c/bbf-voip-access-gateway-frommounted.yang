submodule bbf-voip-access-gateway-frommounted {
  yang-version 1.1;
  belongs-to bbf-sip-voip-frommounted  {
	prefix bbf-sip-voip-frommounted;
  }

  import bbf-yang-types {
    prefix bbf-yang;
  }
  
  include bbf-sip-types-frommounted;
  include bbf-voip-service-providers-frommounted;
  include bbf-sip-server-pool-frommounted;
  include bbf-sip-voip-base-frommounted;

  
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains the Yang definitions to manage the 
	 Voip Access Gateway (VAG) profile.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2026-03-01 {
    description
      "Added yang leaf to configure the name of the vendor";
    reference
      "TR-383a10: Common YANG Modules
       <https://www.broadband-forum.org/technical/download/
       TR-383_Amendment-10.pdf>";
  }

  revision 2020-03-06 {
    description
      "Initial revision.
       * Approval Date:    see revision date above.
       * Publication Date: 2020-03-06.";
    reference
      " ";
  }     


  grouping vag-spec-parameters {
    leaf voip-service-provider {
        type string;
          description
               "Uniquely identifies the Voip Service Provider.";
    }
    leaf vag-sip-register-profile {
      type string;
 	  description
 		"References the sip register characteristics profile.";
    }
    leaf vag-primary-site-first-hop-sip-servers {
      type string;
	  description
	    "References a pool of primary First Hop sip servers
		 for this VAG.";		
    }
    leaf vendor {
      type bbf-yang:string-ascii64 {
        length "4";
        pattern "[A-Z]*";
      }
      description
          "Identifies the vendor. The format is four ASCII coded 
              alphabetic characters [A..Z] as defined in [ATIS-0300220].
              If not present, the vendor is not specified or unknown.";
         reference
             "ITU-T G.988 Clause 9.9.3 - Softswitch";
    }
  }
  
  grouping voip-access-gateway {
    description
      "Defines the parameters included in the voip access 
	   gateway specific profile.";   
	uses vag-spec-parameters;
  }    
}
