module nokia-sdan-power-over-ethernet-control-mounted {
  yang-version 1.1;
  namespace "http://www.nokia.com/Fixed-Networks/BBA/yang/"
             + "nokia-sdan-power-over-ethernet-control-mounted";
  prefix nokia-poe-ctr-mounted;

  import bbf-hardware-types {
    prefix bbf-hwt;
  }
  
  import nokia-hardware-identities {
    prefix nokia-hwi;
  }

  import ietf-hardware-mounted {
    prefix hw-mounted;
  }

  import bbf-fiber-onu-emulated-mount {
    prefix onu;
  }

  
  organization
    "Nokia";

  contact
    "Comments or questions about this Broadband Forum YANG module
     should be directed to <mailto:isam.yang@nokia.com>.";

  description
    "This module contains a collection of YANG definitions for
     Power over Ethernet control(POE).

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

  revision 2025-04-15 {
    description
      "extend the type range of yang leaf pse-class-control";
    reference
      "Epic BBN-207669";
  }

  revision 2024-09-11 {
    description
      "remove operational data related when statement";
    reference
      "BBN-107706";
  }

  revision 2022-01-18 {
    description
      "Initial revision.";
   reference
      "Nokia specific";
  }
  
  augment "/onu:onus/onu:onu/onu:root/hw-mounted:hardware/hw-mounted:component" {
    when "starts-with(hw-mounted:class, 'bbf-hwt:rj45') or 
          starts-with(hw-mounted:class, 'nokia-hwi:rj45')";
    description 
      "Augment model for configurations for 
       power over ethernet.";
    container poe {
      presence "poe";
      description
        "Controls the PoE capability of a power-sourcing 
         equipment (PSE).";
      reference 
        "ITU-T G.988 9.5.6 Power over Ethernet control.";
      leaf enable {
        type boolean;
        default "false";
        description
          "This leaf controls whether power is provided to external 
           equipment over this Ethernet UNI.";
        reference 
          "ITU-T G.988 9.5.1 Physical path termination point 
           Ethernet UNI: Power control.";
      }
      leaf pse-class-control {
        type uint16 {
            range "0..9";
        }
        description
          "Used to place specific limits on the class of power 
           supported by this port. Optional leaf.
           0: Power Feed Enabled at default level.
           1: Power Feed Enabled at Class 0 power level.
           2: Power Feed Enabled at Class 1 power level.
           3: Power Feed Enabled at Class 2 power level.
           4: Power Feed Enabled at Class 3 power level.
           5: Power Feed Enabled at Class 4 power level.
           6: Power Feed Enabled at Class 5 power level.
           7: Power Feed Enabled at Class 6 power level.
           8: Power Feed Enabled at Class 7 power level.
           9: Power Feed Enabled at Class 8 power level. ";
        reference 
          "ITU-T G.988 9.5.6 Power over Ethernet control: 
           PsE class control.";
      }
      leaf power-priority {
        type enumeration {
          enum "critical" {
            description
              "Indicates that the most highst power priority.";
          }
          enum "high" {
            description
              "Indicates that the high power priority.";
          }
          enum "low" {
            description
              "Indicates that the low power priority.";
          }
        }
        description
          "This leaf controls the priority of the port from the point
           of view of a power management algorithm. The priority that
           is set by this leaf could be used by a control mechanism 
           that prevents overcurrent situations by first disconnecting
           ports with lower power priority (higher numerical value).
           Optional leaf.";
        reference 
          "ITU-T G.988 9.5.6 Power over Ethernet control: Power priority.";
      }
    }
  }

  augment "/onu:onus/onu:onu/onu:root/hw-mounted:hardware-state/hw-mounted:component" {
    description 
      "Augments state model with specific power over 
       ethernet operational state nodes.";
    container poe {
      description
        "Monitors the PoE capability  status of a power-sourcing 
         equipment (PSE).";
      reference 
        "ITU-T G.988 9.5.6 Power over Ethernet control.";
      leaf poe-capabilities {
        type bits {
          bit pinout-alternative  { position 0; description "pinout-alternative";}
        }
        description
          "This leaf indicates the PoE capabilities of the port.
           Bit 1:    0 means PSE pinout is fixed. 1 means PSE pinout 
           is controllable.
           Bit2..16: Reserved";
        reference 
          "ITU-T G.988 9.5.6 Power over Ethernet control: PoE capabilities.";
      }
      leaf power-pair-pinout-control {
        type enumeration {
          enum "signal-pairs" {
            description
              "Pinout Alternative A (signal pairs).";
          }
          enum "spare-pairs" {
            description
              "Pinout Alternative B (spare pairs).";
          }
        }
        description
          "Indicates the actual Power Pair Pinout of the port.";
        reference 
          "ITU-T G.988 9.5.6 Power over Ethernet control: Power pair 
           pinout control.";
      }
      leaf power-classification-status {
        type uint16;
        description
          "This leaf indicates the powered device (PD) class of a 
           detected PD.
           0: Undefined or feature not supported
           1: Class 0 PD
           2: Class 1 PD
           3: Class 2 PD
           4: Class 3 PD
           5: Class 4 PD
           6: Class 5 PD
           7: Class 6 PD
           8: Class 7 PD
           9: Class 8 PD
           Other values are reserved.";
        reference 
          "ITU-T G.988 9.5.6 Power over Ethernet control: Power 
           classification status.";
      }
      leaf current-power-consumption {
        type uint32;
        units "milliwatts";
        description
          "This leaf is used to report, in milliwatts, the actual 
           power being provided by this port.";
        reference 
          "ITU-T G.988 9.5.6 Power over Ethernet control: Current
           Power Consumption.";
      }
      leaf power-detection-status {
        type enumeration {
          enum "PSE-disabled" {
            description
              "PSE disabled.";
        }
          enum "PSE-searching" {
            description
              "PSE searching.";
          }
          enum "delivering-power" {
            description
              "PSE delivering power.";
          }
          enum "test-mode" {
            description
              "PSE test mode.";
          }
          enum "fault-detected" {
            description
              "PSE fault detected.";
          }
          enum "specific-fault-detected" {
            description
              "PSE implementation specific fault detected";
          }
        }
        description
          "This leaf indicates the current status of the port.";
        reference 
          "ITU-T G.988 9.5.6 Power over Ethernet control: Power 
           detection status.";
      }
      leaf oper-status {
        type enumeration {
          enum enabled {
            description
              "PPTP is performing its POE function.";
          }
          enum disabled {
            description
              "PPTP is unable to perform its POE function.";
          }
        }
        description
          "This leaf indicates whether the PPTP is capable of 
           performing its function.";
        reference 
          "ITU-T G.988 9.5.6 Power over Ethernet control: Operational state.";
      }
      container status-counter{
        description
          "This counters in this container indicate that the number of
           PoE state machine enters a specific state";
        leaf invalid-signature{
          type uint16;
          description
            "This counter increments when the PoE state machine depicted
             in Figure 33-6 of [IEEE 802.3] enters the signature_invalid
             state.";
          reference 
            "ITU-T G.988 9.5.6 Power over Ethernet control: Invalid 
             signature counter.";
        }
        leaf power-denied {
          type uint16;
          description
            "This counter increments when the PoE state machine 
             depicted in Figure 33-6 of [IEEE 802.3] enters the 
             power_denied state.";
          reference 
            "ITU-T G.988 9.5.6 Power over Ethernet control: 
             Power denied counter.";
        }
        leaf overload {
          type uint16;
          description
            "This counter increments when the PoE state machine 
             depicted in Figure 33-6 of [IEEE 802.3] enters the
             error_delay_over state.";
          reference 
            "ITU-T G.988 9.5.6 Power over Ethernet control: 
             Overload counter.";
        }
        leaf short {
          type uint16;
          description
            "This counter increments when the PoE state machine 
             depicted in Figure 33-6 of [IEEE 802.3] enters the 
             error_delay_short state.";
          reference 
            "ITU-T G.988 9.5.6 Power over Ethernet control: Short 
            counter.";
        }
        leaf MPS-absent {
          type uint16;
          description
            "This counter increments when the PoE state machine 
             depicted in Figure 33-6 of [IEEE 802.3] goes from the 
             state power_on to the idle state.";
          reference 
            "ITU-T G.988 9.5.6 Power over Ethernet control: 
             MPS absent counter.";
        }
      }
    }
  }
}
