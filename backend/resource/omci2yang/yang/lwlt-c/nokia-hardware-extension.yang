module nokia-hardware-extension {
  yang-version 1.1;

  namespace "http://www.nokia.com/Fixed-Networks/BBA/yang/"
  + "nokia-hardware-extension";

  prefix nokia-hw-ext;

  import ietf-hardware {
    prefix hw;
  }
  import bbf-hardware-types {
    prefix bbf-hwt;
  }
  import iana-hardware {
    prefix ianahw;
  }
  import nokia-hardware-profiles {
    prefix nokia-hw-prof;
  }
  import nokia-hardware-identities {
    prefix nokia-hwi;
  }
  import ietf-yang-types {
    prefix yang;
  }

  organization
    "Nokia";

  contact
     "Comments or questions about this Nokia YANG module should be 
     directed to <mailto:isam.yang@nokia.com>.";


  description
     "This module contains a collection of YANG definitions for 
     supporting Nokia specific requirements as applicable to its 
     access network equipment.
     
     Specifically, this module augments the hardware model with 
	 additional identifying operational data of a component.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2022, Nokia. All Rights Reserved.";


  revision 2022-11-28 {
       description
         "Introducing hardware component reset specific
          state data parameters";
       reference
         "Nokia specific.";
  }

  revision 2022-11-23 {
       description
         "Introducing reset-to-factory-datastore if-feature";
       reference
         "Nokia specific. EPIC BBN-58976";
  }

  revision 2021-12-13 {
       description
         "Setting config=false into specific yang leaves";
       reference
         "Nokia specific. EPIC BBN-701";
  }

revision 2021-12-13 {
       description
         "Reuse LT yang files for setting tca-profiles in ONU side && add config=false statement in respective yang leaves";
       reference
         "Nokia specific. EPIC BBN-701";
  }

  revision 2021-09-27 {
       description
         "if-feature uptime moved to container hardware-duration-in-operation";
       reference
         "Nokia specific. EPIC BBN-5857";
  }

  revision 2021-09-16 {
       description
         "Introducing sensor-temp-threshold if-feature";
       reference
         "Nokia specific. EPIC BBN-5857";
  }

  revision 2021-09-06 {
       description
         "Removed local-network-address leaf node from module hardware state and,
          added same into chassis and board hardware state";
       reference
         "Nokia specific. EPIC BBN-772";
  }

  revision 2021-06-25 {
       description
         "als-enabled descripion change";
       reference
         "Nokia specific. EPIC BBN-766";
  }

  revision 2021-03-25 {
       description
         "TCA parameter rxpower migration from rssi";
       reference
         "Nokia specific. EPIC BBN-682";
  }

  revision 2021-03-17 {
       description
         "Moving tx-power-dbm , rx-power-dbm to nokia-hardware-transceivers-dbm.yang";
       reference
         "Nokia specific. EPIC BBN-1693";
  }

  revision 2021-03-08 {
       description
         "Support transceiver rx-power and tx-power in 0.1dBm Units";
       reference
         "Nokia specific. RCR ALU02739128";
  }

  revision 2021-02-17 {
     description
       "TCA parameters units for Temperature, Voltage and TxBias is changed.";
     reference
       "Nokia specific. EPIC BBN-682";
  }

  revision 2020-11-26 {
       description
         "Configurable TCA parameters";
       reference
         "Nokia specific. RCR ALU02503366";
  }

  revision 2020-11-12 {
       description
         "Introducing als if-feature";
       reference
         "Nokia specific. RCR ALU02722973";
  }

  revision 2020-09-10 {
       description
         "Introducing self-test if-feature";
       reference
         "Nokia specific. RCR ALU02678607";
  }

  revision 2020-09-03 {
       description
         "Introducing last-self-test-error field to display reset-with-self-test result";
       reference
         "Nokia specific. RCR ALU02678607";
  }

  revision 2020-06-04 {
       description
         "if-feature update on uptime monitoring leaf nodes.";
       reference
         "Nokia specific. RCR ALU02615153";
  }

  revision 2020-06-03 {
       description
         "Enclosing uptime monitoring leaf nodes in container.";
       reference
         "Nokia specific. RCR ALU02615153";
  }

  revision 2020-04-28 {
       description
         "Change in names of uptime monitoring leaf nodes.";
       reference
         "Nokia specific. RCR ALU02615153";
  }

  revision 2020-03-27 {
       description
         "Activation time and uptime  addition to hardware-state.";
       reference
         "Nokia specific. RCR ALU02615153";
  }

  revision 2020-02-26 {
        description
          "rssi threshold units changed to int16.";
        reference
          "Nokia specific. RCR ALU02503367";
  }

  revision 2020-02-06 {
       description
         "RSSI profile addition, trancsevier-link types.";
       reference
         "Nokia specific. RCR ALU02503367";
  }

  revision 2018-09-13 {
    description
      "Make updates based upon comment resolution about raise or clear alarm when board temperature is over threshold.";
    reference
      "Nokia specific. RCR ALU02451272";
  }

  revision 2017-12-08 {
    description
      "Initial revision.";
    reference
      "Nokia specific";
  }

  typedef tca-transceiver-profile-ref {
    type leafref {
      path "/nokia-hw-prof:tca-profiles/nokia-hw-prof:transceiver-tca-profile/nokia-hw-prof:name";
     }

     description
       "A reference to a tca transceiver profile.";
  }

  typedef tca-transceiver-link-profile-ref {
    type leafref {
      path "/nokia-hw-prof:tca-profiles/nokia-hw-prof:transceiver-link-tca-profile/nokia-hw-prof:name";
     }

     description
       "A reference to a tca transceiver-link profile.";
  }

  feature tca-profiles {
    description
      "Indicates support for tca profiles.";
  }

  feature uptime {
    description
      "Indicates support for hardware uptime.";
  }

  feature self-test {
    description
      "Indicates support for hardware self-test.";
  }

  feature als {
    description
      "Indicates support for automatic laser shutdown per transceiver.";
  }

  feature sensor-temp-threshold {
    description
      "Indicates support for sensor-temp-thresholds.";
  }

  feature reset-to-factory-datastore {
    description
      "Indicates support for hardware reset to factory datastore.";
  }

  augment "/hw:hardware-state/hw:component" {
      when "derived-from-or-self(hw:class,'ianahw:module')";

    description
      "Augment the module hardware state with NOKIA specific remote inventory data.";

      leaf sensor-temp-threshold-high {
          if-feature "sensor-temp-threshold";
          type int32;
          description
            "The threshold is involved in protecting the system against overheating. The sensor-temp-threshold-high is the threshold to raise the overheat alarm.";
      }

      leaf sensor-temp-threshold-high-clear {
          if-feature "sensor-temp-threshold";
          type int32;
          description
            "The threshold is involved in indicating the overheating is eliminated. The sensor-temp-threshold-high-clear is the threshold to clear the overheat alarm.";
      }

      leaf sensor-temp-threshold-low {
          if-feature "sensor-temp-threshold";
          type int32;
          description
            "The threshold is involved in protecting the system against overcooling. The sensor-temp-threshold-low is the threshold to raise the overcool alarm.";
      }

      leaf sensor-temp-threshold-low-clear {
          if-feature "sensor-temp-threshold";
          type int32;
          description
            "The threshold is involved in indicating the overcooling is eliminated. The sensor-temp-threshold-low-clear is the threshold to clear the overcool alarm.";
      }

      leaf ont-serial-num-base {
        type string;
        description
          "ONT serial number base.";
      }

      leaf fim {
        type string;
        description
          "Format Identifier Manufacturing.";
      }

      leaf factory-id {
        type string;
        description
          "Identification code of the factory who manufactured the component.";
      }

      leaf clei-code {
        type string;
        description
          "Common Language Equipment Identifier code.";
      }
      container hardware-duration-in-operation
      {
        if-feature "uptime";
        description
          "Container providing information about hardware component duration-in-operation";

        leaf duration-in-operation {
          type uint16;
          units "weeks";
          description
            "Indicates accumulated duration of hardware component is in operation. The 'duration-in-operation' is being monitored and accumulated from the time indicated by the 'start-duration-in-operation-monitoring'.";
        }

        leaf start-duration-in-operation-monitoring {
          type yang:date-and-time;
          description
            "Indicates start time of hardware component 'duration-in-operation'  monitoring. Monitoring  of hardware component starts after  installation of new hardware. For pre-installed hardware the monitoring starts after software upgrade to the release where this feature is made available, hence the need for this leaf. The 'start-duration-in-operation-monitoring' is stamped based on NTP synchronization. Any historical start time of hardware component prior to the 'start-duration-in-operation-monitoring' is not taken into account.";
        }
      }

      leaf customer-serial-num {
        type string;
        description
          "The customer-specific serial number string for the component.";
      }

      leaf last-self-test-error {
        if-feature "self-test";
        type string;
        description
          "Indicates last self test error. As long as there has been no failing selftest, the value of this
          Leaf would be 00:00:00:00 Any other value indicates the last failed test information
          which needs to be further checked and correlated with OFLT(offline test) document.";
      }
  }


  augment "/hw:hardware-state/hw:component" {
      when "derived-from-or-self(hw:class,'ianahw:chassis') or
            derived-from-or-self(hw:class,'bbf-hwt:board')";
      description
        "Augment the chassis or board hardware-state with Nokia specific local network address.";

       leaf local-network-address {
         type string;
         description
           "Address assigned to chassis or board when connected to a local network,
            address assigned to chassis indicates system mac.";
       }
  }

  augment "/hw:hardware-state/hw:component" {
     description
       "Augment the hardware-state with Nokia specific reset parameters.";

     container component-last-reset-info {
       presence
        "Presence of this container indicates that component
         has reset info parameters associated with it.";

       description
        "contains information on component reset.";

        leaf reset-reason {
           type identityref {
             base nokia-hwi:reset-reason;
           }
           description
            "Indicates reason for hardware component reset.";
        }

        leaf reset-type {
          type identityref {
           base nokia-hwi:reset-type;
          }
          description
            "Indicates reset type of hardware component.";
       }

       leaf reset-info {
         type string;
          description
           "Provides additional information on the reset.";
       }

       leaf reset-triggered-time {
         type yang:date-and-time;
          description
           "Indicates the time the reset was triggered.";
       }

       leaf hardware-ready-time  {
         type yang:date-and-time;
          description
          "Indicates the time when hardware component is ready and operational.";
      }
    }
  }

  augment "/hw:hardware-state/hw:component" {
    when "derived-from-or-self(hw:class,'bbf-hwt:transceiver')";
    description
      "Augment the transceiver hardware-state with NOKIA specific temperature and voltage threshold values.";

     leaf temperature-low-alarm {
        if-feature "tca-profiles";
        type int32;
        units "0.001 degrees Celsius";
        config false;
        description
          "Indicates the low alarm threshold value that is considered for raising tca alarms.";
     }

     leaf temperature-high-alarm {
        if-feature "tca-profiles";
        type int32;
        units "0.001 degrees Celsius";
        config false;
        description
          "Indicates the high alarm threshold value that is considered for raising tca alarms.";
     }

     leaf temperature-low-warning {
        if-feature "tca-profiles";
        type int32;
        units "0.001 degrees Celsius";
        config false;
        description
          "Indicates the low warning threshold value that is considered for raising tca alarms.";
     }

     leaf temperature-high-warning {
        if-feature "tca-profiles";
        type int32;
        units "0.001 degrees Celsius";
        config false;
        description
          "Indicates the high warning threshold value that is considered for raising tca alarms.";
     }

     leaf voltage-low-alarm {
        if-feature "tca-profiles";
        type uint16;
        units "100 uV";
        config false;
        description
          "Indicates the low alarm threshold value that is considered for raising tca alarms.";
     }

     leaf voltage-high-alarm {
        if-feature "tca-profiles";
        type uint16;
        units "100 uV";
        config false;
        description
          "Indicates the high alarm threshold value that is considered for raising tca alarms.";
     }

     leaf voltage-low-warning {
        if-feature "tca-profiles";
        type uint16;
        units "100 uV";
        config false;
        description
          "Indicates the low warning threshold value that is considered for raising tca alarms.";
     }

     leaf voltage-high-warning {
        if-feature "tca-profiles";
        type uint16;
        units "100 uV";
        config false;
        description
          "Indicates the high warning threshold value that is considered for raising tca alarms.";
     }
  }

  augment "/hw:hardware/hw:component" {
    when "derived-from-or-self(hw:class,'bbf-hwt:transceiver')";
    description
      "Augment the trasceiver hardware with NOKIA specific configuration parameters.";

    leaf tca-transceiver-profile {
       if-feature "tca-profiles";
       type tca-transceiver-profile-ref;
       description
         "Reference to a tca transceiver configuration profile.";
    }

     leaf als-enabled {
        if-feature "als";
        type boolean;
        default true;
        description
          "Indicates whether automatic laser shutdown is enabled or disabled per transceiver.
           Takes effect when configured on optical ethernet transceiver, ignored if transceiver 
           is of type electrical or GPON or NGPON.";
     }

     leaf tca-monitoring-enabled {
       if-feature "tca-profiles";
       type boolean;
       default false;
       description
         "Indicates whether transceiver's voltage, temperature, transceiver-link tca parameters rx-power,tx-power, bias-current monitoring is enabled or disabled per transceiver. When enabled, current values are compared with the defined thresholds to raise alarm incase crossing defined thresholds. ";
     }
  }

  augment "/hw:hardware-state/hw:component" {
    when "derived-from-or-self(hw:class,'bbf-hwt:transceiver-link')";
    description
      "Augment the transceiver-link hardware state with NOKIA specific rx-power threshold values.";

     leaf rx-power-low-alarm {
        if-feature "tca-profiles";
        type int16;
        units "0.1 dBm";
        config false;
        description
          "Indicates the low alarm threshold value that is considered for raising rx-power alarms.";
     }

     leaf rx-power-high-alarm {
        if-feature "tca-profiles";
        type int16;
        units "0.1 dBm";
        config false;
        description
          "Indicates the high alarm threshold value that is considered for raising rx-power alarms.";
     }

     leaf rx-power-low-warning {
        if-feature "tca-profiles";
        type int16;
        units "0.1 dBm";
        config false;
        description
          "Indicates the low warning threshold value that is considered for raising rx-power alarms.";
     }

     leaf rx-power-high-warning {
        if-feature "tca-profiles";
        type int16;
        units "0.1 dBm";
        config false;
        description
          "Indicates the high warning threshold value that is considered for raising rx-power alarms.";
     }

     leaf tx-power-low-alarm {
        if-feature "tca-profiles";
        type int16;
        units "0.1 dBm";
        config false;
        description
          "Indicates the low alarm threshold value that is considered for raising tca alarms.";
     }

     leaf tx-power-high-alarm {
        if-feature "tca-profiles";
        type int16;
        units "0.1 dBm";
        config false;
        description
          "Indicates the high alarm threshold value that is considered for raising tca alarms.";
     }

     leaf tx-power-low-warning {
        if-feature "tca-profiles";
        type int16;
        units "0.1 dBm";
        config false;
        description
          "Indicates the low warning threshold value that is considered for raising tca alarms.";
     }

     leaf tx-power-high-warning {
        if-feature "tca-profiles";
        type int16;
        units "0.1 dBm";
        config false;
        description
          "Indicates the high warning threshold value that is considered for raising tca alarms.";
     }

     leaf tx-bias-low-alarm {
        if-feature "tca-profiles";
        type uint32;
        units "1 uA";
        config false;
        description
          "Indicates the low alarm threshold value that is considered for raising tca alarms.";
     }

     leaf tx-bias-high-alarm {
        if-feature "tca-profiles";
        type uint32;
        units "1 uA";
        config false;
        description
          "Indicates the high alarm threshold value that is considered for raising tca alarms.";
     }

     leaf tx-bias-low-warning {
        if-feature "tca-profiles";
        type uint32;
        units "1 uA";
        config false;
        description
          "Indicates the low warning threshold value that is considered for raising tca alarms.";
     }

     leaf tx-bias-high-warning {
        if-feature "tca-profiles";
        type uint32;
        units "1 uA";
        config false;
        description
          "Indicates the high warning threshold value that is considered for raising tca alarms.";
     }
  }

  augment "/hw:hardware/hw:component" {
    when "derived-from-or-self(hw:class,'bbf-hwt:transceiver-link')";
    description
      "tca configuration parameters.";

     leaf tca-transceiver-link-profile {
        if-feature "tca-profiles";
        type tca-transceiver-link-profile-ref;
        description
          "Reference to a tca transceiver-link configuration profile.";
     }
  }

}
