module nokia-sdan-802-dot1x-ext-dynamic-authorization-common-dev {
  yang-version 1.1;
  namespace "http://www.nokia.com/Fixed-Networks/BBA/yang/"
          + "nokia-sdan-802-dot1x-ext-dynamic-authorization-common-dev";
  prefix "nokia-dyn-auth-ext-common-dev";

  import ietf-interfaces {
    prefix "if";
  }

  import ieee802-dot1x {
    prefix "dot1x";
  }

  import nokia-sdan-802-dot1x-ext-dynamic-authorization {
    prefix nokia-dyn-auth-ext;
  }

  import nokia-sdan-radius-dynamic-authorization-types {
    prefix "nokia-dyn-auth-types";
  }

  import nokia-802-dot1x-ext {
    prefix "nokia-dot1x-ext";
  }

  organization
    "Nokia";

  contact
    "Comments or questions about this Nokia YANG module should be
     directed to <mailto:isam.yang@nokia.com>.";

  description
    "This module contains a collection of YANG deviations
     related to Radius Dynamic Authorization Server.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

  revision 2025-04-08 {
    description
      "Deviation condition modified";
    reference
      "Nokia specific";
  }

  revision 2024-11-20 {
    description
      "Commets Addressal.";
    reference
      "Nokia specific";
  }

  revision 2024-06-03 {
    description
      "Initial Revision";
    reference
      "Nokia specific";
  }

  /* Only dynamic auth COA is supported */
  deviation "/if:interfaces/if:interface/dot1x:pae/nokia-dyn-auth-ext:dynamic-auth/nokia-dyn-auth-ext:dynamic-auth-control" {
    deviate add {
      must "not (((current() = 'nokia-dyn-auth-types:dynamic-auth-enable-only-coa') or "
        +"(current() = 'nokia-dyn-auth-types:dynamic-auth-enable-coa-and-dm')) and"
        +"(current()/../../nokia-dot1x-ext:ext-authenticator/nokia-dot1x-ext:authentication-mode = 'port'))" {
        error-message "RADIUS CoA is not applicable to port based authentication-mode";
      }
    }
  }
}
