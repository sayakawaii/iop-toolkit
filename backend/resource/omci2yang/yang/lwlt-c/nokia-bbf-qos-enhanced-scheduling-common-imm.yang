module nokia-bbf-qos-enhanced-scheduling-common-imm {

  namespace
    "http://www.nokia.com/Fixed-Networks/BBA/yang/nokia-bbf-qos-enhanced-scheduling-common-imm";

  prefix  nokia-bbf-qos-enhanced-scheduling-common-imm;

  import ietf-interfaces {
    prefix if;
  }

  import bbf-qos-enhanced-scheduling{
    prefix bbf-qos-sched;
  }

  import ietf-immutable {
    prefix im;
  }

  organization
    "Nokia";

  contact
    "isam.yang@nokia.com";

  description
    "This module contains a collection of YANG deviations on top 
     of standard for supporting BBF/bbf-qos-policies YANG module.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017-2018, Nokia. All Rights Reserved.";
 
 revision 2022-11-29 {
    description
      "Add deviation for hqos.";
    reference
      "Nokia specific";
  }

  /* COMMENTED FOR CREATE PERFORMANCE*/
  deviation "/if:interfaces/if:interface/bbf-qos-sched:egress-tm-objects/bbf-qos-sched:select-tm-objects-method/bbf-qos-sched:scheduler"
  {
    description
          "The egress-tm-objects and its child data nodes cannot be modified. The client can delete or remove the egress-tm-objects container and subsequently create the egress-tm-objects container with new configuration values.";
    deviate add {
            im:immutable "create delete";
    }
  }

}
