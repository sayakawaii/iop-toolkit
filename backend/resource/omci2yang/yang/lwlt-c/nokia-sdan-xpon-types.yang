module nokia-sdan-xpon-types{
 yang-version 1.1;
 namespace "urn:broadband-forum-org:yang:nokia-sdan-xpon-types";

prefix nokia-sdan-xpon-types;

import bbf-xpon-types {
    prefix bbf-xpon-types;
}

organization
  "Nokia";

contact
  "Comments or questions about this Nokia YANG module should be
  directed to <mailto:isam.yang@nokia.com>.";

description
  "This specification is published by Nokia under Non-Disclosure
  Agreement(s) (NDA) with specific parties and has to be considered
  as Confidential Information as defined in such NDA. Nokia reserves
  the right to revise this document for any reason, including but
  not limited to conformity with standards promulgated by various
  agencies, utilization of advances in the state of the technical
  areas, or the reflection of changes in the design of any
  equipment, techniques, or procedures described or referred to
  herein.

  The product specifications and other technical or performance
  information contained herein are subject to change without notice.
  Updates of this document will be issued under the above NDA's.

  Nokia makes no representation or warranty, expressed or implied,
  with respect to the sufficiency, accuracy, or utility of any
  information or opinion contained herein. Nokia expressly advises
  that any use of for any purpose or reliance upon this technical
  reference is at the risk of the user and that Nokia shall not be
  liable for any damage or injury incurred by any person arising out
  of the sufficiency, accuracy, or utility of any information or
  opinion contained herein.

  This document is not to be construed as a suggestion to any
  manufacturer to modify or change any of its products, nor does
  this document represent any commitment by Nokia to sell or
  purchase any product. Nothing contained herein shall be construed
  as conferring by implication, estoppel, or otherwise any license
  or right under any patent, whether or not the use of any
  information herein necessarily employs an invention of any
  existing or later issued patent.

  Nokia reserves the right not to offer any or all of these products
  and to withdraw any or all of them at any future time.

  Copyright (C) 2022, Nokia. All Rights Reserved";

revision 2022-03-09 {
  description
    "add Nokia under Non-Disclosure Agreement(s)";
  reference
    "TBD";
}

revision 2021-12-09 {
  description
    "Initial revision.";
  reference
    "TBD";
}

identity twentyfivegs {
    base bbf-xpon-types:channel-pair-type-base;
    description
      "This identity is used to denote a 25GS-PON channel-pair,
       per 25GS-PON MSA";
  }


identity twentyfivegs-channel-pair-line-rate-profile-base {
    description
      "This identity is used to define the possible combinations of
       downstream and upstream line-rates for a
       25GS-PON channel-pair.";
}

identity unplanned-25gs-cp-line-rate {
    base
      nokia-sdan-xpon-types:twentyfivegs-channel-pair-line-rate-profile-base;
    description
      "This identity is used to denote a 25GS-PON channel pair
       with yet undefined downstream and upstream line rates.";
}

identity down-25-up-10 {
    base
      nokia-sdan-xpon-types:twentyfivegs-channel-pair-line-rate-profile-base;
    description
      "This identity is used to denote an 25GS-PON channel-pair
       with DS:25Gbps and US:10Gbps line-rates.";
}

identity down-25-up-25 {
    base
      nokia-sdan-xpon-types:twentyfivegs-channel-pair-line-rate-profile-base;
    description
      "This identity is used to denote an 25GS-PON channel-pair
       with DS:25Gbps and US:25Gbps line-rates.";
}

typedef nokia-composite-downstream-wavelength-type {
    type union {
      type uint32 {
        range "0 | 156000..161000";
      }
      type enumeration {
        enum "25gs-pon" {
          description
            "To be used in case of 25GS-PON.";
        }
      }
    }
    description "type nokia-composite-downstream-wavelength-type";
  }
}
