module nokia-ietf-system-aug-ntp-dev {

  yang-version 1.1;

  namespace "http://www.nokia.com/Fixed-Networks/BBA/yang/"
    + "nokia-ietf-system-aug-ntp-dev";

  prefix  nokia-ietf-system-aug-ntp-dev;

  import ietf-system {
    prefix sys;
  }

  import nokia-ietf-system-aug {
    prefix nokia-ietf-system-aug;
  }
  
  organization
    "Nokia";

  contact
    "isam.yang@nokia.com";

  description
    "The NOKIA IETF/System augment YANG module supporting
     deviations on top of standard.";

  revision 2021-06-30 {
    description
      "Initial revision for disable lt board ntp authentication configuration";
    reference
      "TBD";
  }

  deviation "/sys:system/sys:ntp/nokia-ietf-system-aug:authentication" {
   deviate not-supported;
  }

  deviation "/sys:system/sys:ntp/sys:server/nokia-ietf-system-aug:authentication" {
   deviate not-supported;
  }
  
  deviation "/sys:system/sys:ntp/nokia-ietf-system-aug:authentication-keys" {
   deviate not-supported;
  }

}
