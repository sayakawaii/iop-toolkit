module nokia-sdan-ethernet-loop-detection {
  yang-version 1.1;
  namespace "http://www.nokia.com/Fixed-Networks/BBA/yang/"
           + "nokia-sdan-ethernet-loop-detection";
  prefix nokia-sdan-eld;

  import ietf-yang-types {
    prefix yang;
  }

  import ietf-interfaces {
    prefix if;
  }

  import bbf-dot1q-types {
    prefix bbf-dot1qt;
  }

  import bbf-frame-classification {
    prefix bbf-classif;
  }


  organization
    "Nokia";

  contact
    "Comments or questions about this Nokia YANG module should be
     directed to <mailto:isam.yang@nokia.com>.";

  description
    "This module contains a collection of YANG definitions for
     supporting Nokia specific requirements as applicable to its
     access network equipment.

     Specifically, this module defines configuration and operational
     state data for ethernet loop detection.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

  revision 2024-11-06 {
    description
      "Initial revision.";
    reference
      "Nokia specific.";
  }

  identity loop-detect-action-type {
    description "Base identity to represent the action to take when a loop is detected.";
  }

  identity shut-down {
    base loop-detect-action-type;
    description "Shuts down the port to disable it from receiving and sending frames.";
  }

  identity no-action {
    base loop-detect-action-type;
    description "No action on the port.";
  }

  identity port-state-change-type {
    description
      "Base identity to represent current port state based on loop detection.";
  }

  identity un-block {
    base port-state-change-type;
    description "No traffic impact.";
  }

  identity blocked {
    base port-state-change-type;
    description "Traffic has been blocked.";
  }

  container ethernet-loop-detection {
    description "Ethernet loop detection configuration.";

    list interfaces {
      key "name";
      description "List of physical Ethernet interfaces for loop detection.";

      leaf name {
        type if:interface-ref;
        description "Reference to an Ethernet physical network port interface.";
      }

      leaf loop-detection-action {
        type identityref {
          base loop-detect-action-type;
        }
        default no-action;
        description "Action to take when a loop is detected in tagged/untagged frames.";
      }

      container statistics {
        config false;
        description
          "Statistics information of interface.";

        leaf port-traffic-state {
          type identityref {
            base port-state-change-type;
          }
          description
            "Current port state based on loop detection.";
        }

        leaf total-sent-frames {
          type yang:counter64;
          description
            "A count of all frames transmitted through the port.";
        }

        leaf total-received-frames {
          type yang:counter64;
          description
            "A count of all frames received through the port.";
        }
        leaf total-dropped-frames {
          type yang:counter64;
          description
            "A count of all frames dropped through the port.";
        }
      }

      list vlan-list {
        key "name";
        description "List of VLAN's configured for each interface.";
        leaf name {
          type string;
          description "Name of VLAN list.";
        }
        list vlan-tag {
          key "index";
          min-elements 1;
          max-elements 2;
          description
            "The tags to match, with the outermost tag to match 
             assigned index 0.";

          leaf index {
            type bbf-classif:tag-index;
            must "count(../../vlan-tag[index = 0]) > 0" {
              error-message
                "An inner tag can only be matched on when also 
                 matching on an outer tag.";
              description
                "Only allow matching on an inner tag, if also 
                 matching on the outer tags at the same time.";
            }
            description
              "The index into the tag stack, index '0' for outer
               tag, index '1' for inner tag.";
          }
          leaf vlan-id {
            type bbf-dot1qt:vlan-id;
            mandatory true;
            description
              "Allowed VLAN-IDs.";
          }
          leaf pbit {
            type union {
              type bbf-dot1qt:pbit-list;
              type enumeration {
              enum "any" {
                description
                  "Matches any pbit value in the range of 0 to 7.";
                }
              }
            }
            default "any";
            description
              "Allowed PBIT values.";
          }
          leaf dei {
            type union {
              type bbf-dot1qt:dei;
              type enumeration {
              enum "any" {
                description
                  "Matches any Drop Eligible Inidicator (DEI) 
                   value, i.e. value 0 or 1.";
                }
              }
            }
            default "any";
            description
              "Allowed DEI values.";
          }
        }
      }
    }
  }
}
