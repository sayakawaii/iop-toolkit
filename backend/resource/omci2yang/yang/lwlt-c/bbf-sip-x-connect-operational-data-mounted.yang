submodule bbf-sip-x-connect-operational-data-mounted {
  yang-version 1.1;
  belongs-to bbf-sip-voip-mounted  {
    prefix bbf-sip-voip-mounted;
  }
  
  import ietf-inet-types {
    prefix inet;
	reference
      "RFC 6991: Common YANG Data Types.";
  }
  
  import ietf-yang-types {
    prefix yang;
  }
  
  organization
    "Broadband Forum <https://www.broadband-forum.org>
     Common YANG Work Area";

   contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";


  description
    "This submodule contains a collection of YANG definitions for
     viewing the operational data of sip connections.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2020-03-06 {
    description
      "Initial revision.
       * Approval Date:    see revision date above.
       * Publication Date: 2020-03-06.";
    reference
      " ";
  }

  grouping sip-x-connect-operational-data {
	leaf sip-remote-ip-version {
	  type inet:ip-version;
	  description
		"The ip version of the first hop Sip server used by the
		 cross-connection.";
	}
	leaf sip-remote-ip-prefix {
	  type inet:ip-prefix;
	  description
		"The ip address prefix of the first hop Sip server  
		 used by the cross-connection.";
	}
	leaf sip-remote-ip-address {
	  type inet:ip-address;
	  description
	    "The remote ip address of the first hop Sip server in 
		 used by the cross-connection.";	
	}
	leaf sip-remote-port-used {
	  type uint16;
	  description
	    "The port of the first hop Sip server used by the 
		 cross-connection.";
	}
	leaf sip-transport-used {
	  type uint16;
	  description
	    "The transport type used for the cross-connection.";
	}
	leaf session-start-time {
	  type yang:date-and-time;
	  description
	    "Start time of the session. 
		 - For outgoing successful calls : the moment that ACK to 
		   200 OK (Initial INVITE) is received.
		 - For outgoing unsuccessful calls : the moment that the 
		   Initial INVITE is sent. 
         - For incoming successful calls : the moment that ACK to 
		   200 OK (Initial INVITE) is sent.
         - For incoming unsuccessful calls: the moment that 180 
		   Ringing is sent.";
	}
	leaf calling-number {
	  type string;
	  description
	    "For outgoing calls the calling party number is the Sip AOR
 		 of the calling party.
         For incoming calls the calling party number is the 
		 user@domain present in P-Asserted-Identity or From header
         of the Sip message.";		  
	}
	leaf called-number {
	  type string;
	  description
	    "For outgoing calls the called party number are the dialed
		 digits of the called party.
         For incoming calls the called party number is the Sip
		 AOR of called party.";
	}
    leaf session-direction {
      type enumeration {
	    enum incoming {
		  value 1;
		  description
		    "Indicates if the established connection is an incoming
			 call.";
		}
		enum outgoing {
		value 2;
		  description
		    "Indicates if the established connection is an outgoing
			 call.";
		}
	  }
	  description
	    "The session direction indicates of the established call is
		 an incoming call or an outgoing call.";
    }
	leaf session-duration {
	  type uint16;
	  units "1 second";
	  description
	    "The total call duration.";
	}
	leaf session-failure-reason {
	  type string;
	  description
	    "In case the session was successful, there will be no failure
		 reason.
 		 Otherwise the session failure reason will reflect the reason
		 for the failing call attempt:
         - Final failure response received, being 3xx, 4xx, 5xx or 
		   6xx response received (=sip response code),
         - Timer B expiry (no response received),
         - Cancelled/terminated call attempt (by going on-hook before 
		   session established).";
    } 
  }
}
