module nokia-uni-loop-detection-frommounted {
  yang-version 1.1;
  namespace "http://www.nokia.com/Fixed-Networks/BBA/yang/"
  + "nokia-uni-loop-detection-frommounted";


  prefix "nokia-loop-detect-frommounted";

  import ietf-interfaces-frommounted {
    prefix if-frommounted;
  }

  import bbf-fiber-onu-emulated-mount {
    prefix onu;
  }

  organization
    "Nokia";

  contact
    "Comments or questions about this Nokia YANG module should be
     directed to <mailto:isam.yang@nokia.com>.";

  description
    "This module contains a collection of YANG definitions for
    supporting Nokia specific requirements as applicable to its
    access network equipment.

    Specifically, this module augments the hardware model with data
    that supports to configure onu level uni loop detection
    functionality.

    This specification is published by Nokia under Non-Disclosure
    Agreement(s) (NDA) with specific parties and has to be considered
    as Confidential Information as defined in such NDA. Nokia
    reserves the right to revise this document for any reason,
    including but not limited to conformity with standards
    promulgated by various agencies, utilisation of advances in the
    state of the technical areas, or the reflection of changes in the
    design of any equipment, techniques, or procedures described or
    referred to herein.

    The product specifications and other technical or performance
    information contained herein are subject to change without
    notice. Updates of this document will be issued under the above
    NDA's.

    Nokia makes no representation or warranty, expressed or implied,
    with respect to the sufficiency, accuracy, or utility of any
    information or opinion contained herein. Nokia expressly advises
    that any use of for any purpose or reliance upon this technical
    reference is at the risk of the user and that Nokia shall not be
    liable for any damage or injury incurred by any person arising
    out of the sufficiency, accuracy, or utility of any information
    or opinion contained herein.

    This document is not to be construed as a suggestion to any
    manufacturer to modify or change any of its products, nor does
    this document represent any commitment by Nokia to sell or
    purchase any product. Nothing contained herein shall be construed
    as conferring by implication, estoppel, or otherwise any license
    or right under any patent, whether or not the use of any
    information herein necessarily employs an invention of any
    existing or later issued patent.

    Nokia reserves the right not to offer any or all of these
    products and to withdraw any or all of them at any future time.

    Copyright (C) 2021, Nokia. All Rights Reserved.";

  revision 2021-11-02 {
    description
      "Initial revision of YANG model for onu to support uni loop
       detection.";
    reference
      "Nokia specific";
  }

  augment "/onu:onus/onu:onu/onu:fromroot/if-frommounted:interfaces" {
    description "augment interfaces for loop detection";
    container uni-loop-detection {
      presence "Presence of this container indicates the ONU's unis loop detection behavior are under control.";
      description
        "Uni loop detection configuration.";

      leaf enable {
        type boolean;
        description
          "This YANG leaf is used to enable/disable
           uni-loop-detect testing for all physical interfaces
           of type equal or derived from 'ianaift:ethernetCsmacd'
           at once.when this YANG leaf is enabled a
           uni-loop-detect test is performed periodic.
           The ONU will report a 'loop-detect-alarm' related to
           affected UNIs as soon such UNIs fail the
           uni-loop-detect test.The ONU will clear the
           'loop-detect-alarm' of affected UNIs if they succeed
           a uni-loop-test or if this YANG leaf is configured as
           'disabled'.";
      }

      leaf auto-shut-off {
        type boolean;
        description
          "This YANG leaf is used to cause interfaces that fail
           the uni-loop-detect test to be automatically put in
           operational state 'down'. In some ONU models, the
           interface might be re-enabled when the uni-test-detect
           'enable' is configured to 'false',however,some ONU
           models maybe not, better read the ONU user manual.";
      }
    }
  }
}
