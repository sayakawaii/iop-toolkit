module bbf-xpon-onumgnt-nodes{
 namespace "urn:broadband-forum-org:yang:bbf-xpon-onumgnt-nodes";
 yang-version 1.1;

prefix bbf-xpon-onumgnt;

    import ietf-interfaces {
        prefix if;
    }

    import bbf-xpon {
        prefix bbf-xpon;
    }

    import bbf-xpon-types {
        prefix bbf-xpon-types;
    }

    organization
        "Nokia";

    contact
        "Comments or questions about this Nokia YANG module should be
        directed to <mailto:isam.yang@nokia.com>.";

    description
        "This module contains a collection of YANG definitions for
        supporting Nokia specific requirements as applicable to its
        access network equipment.

        This specification is published by Nokia under Non-Disclosure
        Agreement(s) (NDA) with specific parties and has to be
        considered as Confidential Information as defined in such NDA.
        Nokia reserves the right to revise this document for any
        reason, including but not limited to conformity with standards
        promulgated by various agencies, utilisation of advances in
        the state of the technical areas, or the reflection of changes
        in the design of any equipment, techniques, or procedures
        described or referred to herein.

        The product specifications and other technical or performance
        information contained herein are subject to change without
        notice.  Updates of this document will be issued under the
        above NDA's.

        Nokia makes no representation or warranty, expressed or
        implied, with respect to the sufficiency, accuracy, or utility
        of any information or opinion contained herein.  Nokia
        expressly advises that any use of for any purpose or reliance
        upon this technical reference is at the risk of the user and
        that Nokia shall not be liable for any damage or injury
        incurred by any person arising out of the sufficiency,
        accuracy, or utility of any information or opinion contained
        herein.

        This document is not to be construed as a suggestion to any
        manufacturer to modify or change any of its products, nor does
        this document represent any commitment by Nokia to sell or
        purchase any product.  Nothing contained herein shall be
        construed as conferring by implication, estoppel, or otherwise
        any license or right under any patent, whether or not the use
        of any information herein necessarily employs an invention of
        any existing or later issued patent.

        Nokia reserves the right not to offer any or all of these
        products and to withdraw any or all of them at any future
        time.

        Copyright (C) 2021, Nokia.  All Rights Reserved.";

revision 2019-12-12 {
  description
    "Initial revision.";
  reference
    "TBD";
}

typedef onu-serial-number-or-all {
    type union {
	    type bbf-xpon-types:onu-serial-number;
	      type enumeration {
	        enum "all" {
	          description
	            "Means all ONUs";
	        }
	      }
	    }
	    description
	      "A type which corresponds either to a specific
	       ONU or, with the keyword 'all', to all ONUs.";
}

augment '/if:interfaces/if:interface/bbf-xpon:channel-termination' {
  description
    "Add-on to configuration of an xPON channel termination.";
 action deactivate-onu {
  description
    "Request a deactivate of the onu.";
       reference
          "ITU-T G.984.3 Section 9.2.1
           ITU-T G.987.3 Table 11.2
           ITU-T G.9807.3 Table C.11.2
           ITU-T G.989.3 Table 11.2";
  input {
        leaf onu-serial-number {
          type onu-serial-number-or-all;
          mandatory true;
          description
            "Indicates the serial number of the ONU
              which must be deactivated or indicates that
              all ONUs present on the channel termination
              must be deactivated.";
        }
   }
      output {
        leaf onu-deactivate-request-status {
          type identityref {
            base bbf-xpon-types:action-request-status;
          }
          description
            "Indicates what the OLT is doing when receiving the
             deactivate request action. The OLT can for instance indicate
             that the request is in progress or has been rejected.";
        }

        leaf onu-deactivate-request-reject-string {
          when
            "../onu-deactivate-request-status
                        != 'bbf-xpon-types:request-being-processed'" {
            description
              "only valid when the OLT has rejected the tune
               request.";
          }
          type string;
          description
            "A text string indicating the reason why the OLT
             rejected the action.";
        }
      }
  }
}

  augment '/if:interfaces/if:interface/bbf-xpon:channel-termination' {
    action reboot-onu {
      description
        "This action requests the OLT to reboot all ONUs or a given ONU
          present on the channel termination, by sending a broadcast or unicast
          '0x1D-Reboot_ONU' PLOAM message. This action is applicable only to channel
          terminations with an xPON type = XGS-PON or NG-PON2.The term 'present' must
          be understood in the sense of the 'onu-present' identity defined in
          'bbf-xpon-onu-types' YANG module. This action is indifferently applicable
          whether the ONU relates to a configured virtual ANI or not.
          In case the targeted ONU is not present, the action is void.";
      reference
        "ITU-T G.9807.3 Table C.11.2, Amendment 2
         ITU-T G.989.3 Table 11.2, Amendment 2";
      input {
        leaf onu-serial-number {
          type onu-serial-number-or-all;
          mandatory true;
            description
              "Indicates the serial number of the ONU
               which must be rebooted or indicates that
               all ONUs present on the channel termination
               must be rebooted.";
        }
      }
      output {
        leaf reboot-onu-request-status {
          type identityref {
            base bbf-xpon-types:action-request-status;
          }
          description
            "Indicates what the OLT is doing when receiving the
             tune request action. The OLT can for instance indicate
             that the request is in progress or has been rejected.";
        }
        leaf reboot-onu-request-reject-string {
          when "not(derived-from-or-self(../reboot-onu-request-status,"
             + "'bbf-xpon-types:request-being-processed'))" {
            description
              "Only valid when the OLT has rejected the request.";
          }
        type string;
          description
            "A text string indicating the reason why the OLT
             rejected the action.";
        }
      }
    }
  }
}
