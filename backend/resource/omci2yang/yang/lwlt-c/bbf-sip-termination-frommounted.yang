submodule bbf-sip-termination-frommounted {
  yang-version 1.1;
  belongs-to bbf-sip-voip-frommounted  {
    prefix bbf-sip-voip-frommounted;
  }
  
  import tailf-common {
    prefix tailf;
  }   
   
  include bbf-sip-voip-base-frommounted;
  include bbf-sip-types-frommounted;
  
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains a collection of YANG definitions for
     managing sip pots terminations.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2021-03-24 {
    description
      "Initial rvision.
       * Approval Date:    see revision date above.
       * Publication Date: 2020-03-06.";
    reference
      " ";
  }

  grouping authentication-settings {
    leaf authentication-scheme {
      type enumeration {
        enum md5-digest {
          value 1;
          description
            "validate using md5 digest authentication.";
        }
      }
      description
		"Authentication validation scheme for user authentication.";
	}
	leaf realm {
      type string {
        length "0..25";
      }
      description
		"The authentication realm.";
	}
	leaf auth-user-name {
      type string {
        length "0..50";
      }
	  description
		"The authentication user name.";
	}
	leaf digest-password {
	  /* type bbf-yang:name-string; */
	  type tailf:aes-cfb-128-encrypted-string;
	  description
		"The authentication password.";
	}
  }
  
  grouping sip-termination-characteristics {    
	description
	  "The characteristics of the SIP termination.";	  
	leaf sip-uni-display-name {
      type string
      {
        length "0..25";
      }
	  description
		"The display name of the SIP user interface.";
	}			
	leaf sip-uni-uri {
      type string
      {
        length "0..50";
      }
	  description
		"The SIP  user interface URI.";
	}	  
    leaf receiver-off-hook-timer {
	  type uint8;
	  units "1 second";
      description
        "Receiver off hook timer (Roh).";	  
	}
  }  
  
  grouping sip-termination {
    uses authentication-settings;
    uses sip-termination-characteristics;
    leaf sip-uni-suppl-services-profile {
      type string;
	  description
		"References the call service profile that applies to the 
		 sip user interface.";
    }	
  }
}
