module nokia-bbf-qos-policies-mounted-eonu-dev {
   namespace
    "http://www.nokia.com/Fixed-Networks/BBA/yang/nokia-bbf-qos-policies-mounted-eonu-dev";

  prefix  nokia-bbf-qos-policies-mounted-eonu-dev;

  import bbf-fiber-onu-emulated-mount {
    prefix onu;
  }

  import ietf-interfaces-mounted {
    prefix if-mounted;
  }

  import bbf-qos-policies-mounted{
    prefix bbf-qos-pol-mounted;
  }


  import bbf-if-type-mounted{
    prefix bbfift-mounted;
  }

  organization
    "Nokia";

  contact
    "isam.yang@nokia.com";

  description
    "This module contains a collection of YANG deviations on top 
     of standard for supporting BBF/bbf-qos-policies YANG module.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.lic-appsufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017-2018, Nokia. All Rights Reserved.";

  /* revision */
  revision 2021-04-08 {
    description
      "Adding Deviations for not supported Yang leaves";
    reference
       "Nokia specific";
  }

  //Only vlan subinterface can attach egress qos profile
  deviation "/onu:onus/onu:onu/onu:root/if-mounted:interfaces/if-mounted:interface/bbf-qos-pol-mounted:egress-qos-policy-profile"{
    description
       "This deviation assures that egress-qos-policy-profile is not supported.";
    deviate not-supported;
  }  

   
  deviation "/onu:onus/onu:onu/onu:root/bbf-qos-pol-mounted:qos-policy-profiles/bbf-qos-pol-mounted:policy-profile/bbf-qos-pol-mounted:policy-list"{
    description
       "This deviation assures that max 2 policies per qos profile can be attached.";
    deviate add{
      max-elements 2;
    }
  }

  deviation "/onu:onus/onu:onu/onu:root/if-mounted:interfaces/if-mounted:interface/bbf-qos-pol-mounted:ingress-qos-policy-profile"
  {
     description
       "This deviaton assures that only vsi can attach qos profile.";
    deviate add{
      must "(current()/../if-mounted:type = 'bbfift-mounted:vlan-sub-interface')"
      {
         error-message "Only vlan subinterface can attach ingress qos profile.";
      }
    }
  }

}
