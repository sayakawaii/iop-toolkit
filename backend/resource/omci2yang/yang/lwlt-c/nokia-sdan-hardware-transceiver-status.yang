module nokia-sdan-hardware-transceiver-status {
  yang-version 1.1;

  namespace "http://www.nokia.com/Fixed-Networks/BBA/yang/"
  + "nokia-sdan-hardware-transceiver-status";

  prefix nokia-sdan-hw-xcvr-status;

  import ietf-hardware {
    prefix hw;
  }

  import bbf-hardware-transceivers {
    prefix bbf-hw-xcvr;
  }

  organization
    "Nokia";

  contact
     "Comments or questions about this Nokia YANG module should be
      directed to <mailto:isam.yang@nokia.com>.";

  description
     "This module contains a collection of YANG definitions for
     supporting Nokia specific requirements as applicable to its
     access network equipment.

     Specifically, this module augments the hardware model with
     status of reading transceiver EEPROM banks.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

  revision 2024-09-18 {
       description
         "Introduced status field to indicate result of
          transceiver/link EEPROM reads";
       reference
         "Nokia specific.";
  }

  /* transceiver inventory and diagnostics status */
  /* ============================================ */

  identity availability-status {
    description
      "Base identity for availability status";
  }

  identity no-error {
    base availability-status;
    description
      "No error, valid values are obtained from transceiver
       EEPROM.";
  }

  identity a0-read-failed {
    base availability-status;
    description
      "The attempt to read the A0 bank of the specified
       transceiver failed. A0 is read to determine if A2
       is supported. so no attempt was made to read the
       A2 information.";
  }

  identity a0-checksum-failed {
    base availability-status;
    description
      "The A0 bank of the transceiver EEPROM is
       corrupted.";
  }

  identity a2-not-supported {
    base availability-status;
    description
      "The A0 bank of the transceiver EEPROM indicates
       A2 is not supported.";
  }

  identity a2-read-failed {
    base availability-status;
    description
      "The attempt to read the A2 bank of the specified
       transceiver failed.";
  }

  identity a2-checksum-failed {
    base availability-status;
    description
      "The A2 bank of the transceiver EEPROM is
       corrupted.";
  }

  identity sw-error {
    base availability-status;
    description
      "Software error.";
  }

  augment "/hw:hardware-state/hw:component/bbf-hw-xcvr:transceiver" {
    description
    "Augment the transceiver hardware state with inventory-
     status field.";

     leaf inventory-status {
       type identityref {
            base availability-status;
       }
       description
         "Indicates status of reading transceiver inventory
          data from A0 bank of EEPROM";
      }
  }

  augment "/hw:hardware-state/hw:component/bbf-hw-xcvr:transceiver/bbf-hw-xcvr:diagnostics" {
    description
    "Augment the transceiver diagnostics hardware state with
     status field.";

     leaf status {
       type identityref {
            base availability-status;
       }
       description
         "Indicates status of reading transceiver diagnostics
          monitoring data from A2 bank of EEPROM.";
     }
  }

  augment "/hw:hardware-state/hw:component/bbf-hw-xcvr:transceiver-link/bbf-hw-xcvr:diagnostics" {
    description
    "Augment the transceiver-link diagnostics hardware state with
     status field.";

     leaf status {
       type identityref {
            base availability-status;
       }
       description
         "Indicates status of reading transceiver-link diagnostics
          monitoring data from A2 bank of EEPROM.";
     }
   }
 }
