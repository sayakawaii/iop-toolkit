module nokia-sdan-hardware-component-test-mounted {
  yang-version 1.1;
    
  namespace "http://www.nokia.com/Fixed-Networks/BBA/yang/"
           + "nokia-sdan-hardware-component-test-mounted";
    
  prefix nokia-sdan-hardware-component-test-mounted;

  import nokia-sdan-hardware-component-test-types {
    prefix nokia-sdan-hwtestt;
  }
  
  import bbf-fiber-onu-emulated-mount {
    prefix onu;
  }
  
  import ietf-hardware-mounted {
    prefix hw-mounted;
  }
 
  import bbf-yang-types {
    prefix bbf-yang;
  }
   
  
  organization
    "Nokia";
    
  contact
    "Comments or questions about this Nokia YANG module should be
     directed to <mailto:isam.mibsupport@nokia.com>.";
    
  description
    "This module contains a collection of YANG definitions for
     supporting Nokia specific requirements as applicable to its
     access network equipment.
    
     Specifically, this module contains a collection of YANG
     definitions for testing IP connectivity.
    
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.
    
     The product specifications and other technical or performance
     information contained herein are subject to change without
     notice. Updates of this document will be issued under the above
     NDA's.
    
     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.
    
     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.
    
     Nokia reserves the right not to offer any or all of these
     products and to withdraw any or all of them at any future time.
    
     Copyright (C) 2021, Nokia. All Rights Reserved.";
    
  revision 2024-09-11 {
    description
      "remove operational data related when statement";
    reference
      "BBN-107706";
  }
    
  revision 2022-10-13 {
    description
      "Initial revision.
       * Approval Date:    see revision date above.
       * Publication Date: yyyy-mm-dd.";
    reference
      "Nokia specific";
  }
   
  augment '/onu:onus/onu:onu/onu:root/hw-mounted:hardware-state/hw-mounted:component' {
    description
      "Augment hardware model with an action to perform a self-test.";
    action self-test{
      description
        "Request a self test of the hardware component.";
      input {
        leaf test-name{
          type bbf-yang:string-ascii64;
          mandatory true;
          description
            "Is the instance name of the self-test action. Since
            the self-test action is executed in asynchronous mode, this
            object is used by the server to associate the self-test action
            instance with a notification message";
        }
      }
    }
        
    notification self-test-result {
      description
        "Indicates that the specified test completed and provides the
         result of this test.";     
      leaf test-name{
        type bbf-yang:string-ascii64;
        mandatory true;
        description
          "Since the self-test action is executed in asynchronous mode,
          this object is used by the server to associate the
          notification message with a self-test action instance";
      }
      leaf self-test-result{
        type identityref{
          base nokia-sdan-hwtestt:self-test-result-base;
        }
        description
          "The result of the self-test.";
      }
    }
  }
}
