module nokia-mgmd-mounted {
  yang-version 1.1;
  namespace "http://www.nokia.com/Fixed-Networks/BBA/yang/"
    + "nokia-mgmd-mounted";
  prefix  nokia-mgmd-mounted;

  import bbf-mgmd-mounted {
    prefix bbf-mgmd-mounted;
  }

  import bbf-fiber-onu-emulated-mount {
     prefix onu;
  }

  organization
    "Nokia";

  contact
    "Comments or questions about this Nokia YANG module should be 
     directed to <mailto:isam.yang@nokia.com>.";

  description
    "This module contains a collection of YANG definitions for 
     supporting Nokia specific requirements as applicable to its 
     access network equipment.
     
     Specifically, this module augments the mounted multicast model
     with a per-subscriber control to enable or disable the G.988
     Multicast subscriber monitor (ME 311) function on the ONU.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2026, Nokia. All Rights Reserved.";

  revision 2026-06-30 {
    description
      "Initial revision. Add per-subscriber leaf
       'mcast-subscriber-monitor-enable' under
       multicast-interface-to-host to enable/disable the G.988 Multicast
       subscriber monitor (ME 311) on the ONU.";
    reference
      "ITU-T G.988 clause 9.3.29 Multicast subscriber monitor.";
  }

  augment '/onu:onus/onu:onu/onu:root/bbf-mgmd-mounted:multicast/bbf-mgmd-mounted:mgmd/bbf-mgmd-mounted:multicast-vpn/bbf-mgmd-mounted:multicast-interface-to-host'
  {
    description
      "Augment the per-subscriber multicast interface to a host with a
       Nokia specific control to enable or disable the G.988 Multicast
       subscriber monitor function for the subscriber on the ONU.";

    leaf mcast-subscriber-monitor-enable {
      type boolean;
      default "false";
      description
        "Enables or disables the Multicast subscriber monitor function
         for this multicast interface to a host (subscriber UNI) on the
         ONU.

         When set to 'true', the OLT instantiates a Multicast subscriber
         monitor (ITU-T G.988 ME 311) for this subscriber, using the
         same managed entity identifier as the MAC bridge port
         configuration data / IEEE 802.1p mapper used by the Multicast
         subscriber config info (ME 310), so that the active multicast
         group list and bandwidth usage of the subscriber can be read
         back.

         When set to 'false' (the default), the monitor is not
         instantiated. If an instance exists on the ONU, the OLT shall
         disable the collection by deleting this instance.";
      reference
        "ITU-T G.988 clause 9.3.29 Multicast subscriber monitor.";
    }
  }
}
