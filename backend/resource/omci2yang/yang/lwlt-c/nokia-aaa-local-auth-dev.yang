module nokia-aaa-local-auth-dev {

    yang-version 1.1;

    namespace
        "http://www.nokia.com/Fixed-Networks/BBA/yang/nokia-aaa-local-auth-dev";

    prefix nokia-aaa-local-auth-dev;

    import nokia-aaa {
        prefix nokia-aaa;
    }

    organization
        "Nokia";

    contact
      "Comments or questions about this Nokia YANG module should be
       directed to <mailto:isam.yang@nokia.com>.";

    description
      "This module contains a collection of YANG definitions for
       supporting Nokia specific requirements as applicable to its
       access network equipment.

       Specifically, this module identifies data that potentially
       contains private data. Note that this classification is product
       independent while the support of this data is product dependent.
       I.e. it might be that data that is identified as private is not
       supported in a particular product variant.

       This specification is published by Nokia under Non-Disclosure
       Agreement(s) (NDA) with specific parties and has to be considered
       as Confidential Information as defined in such NDA. Nokia
       reserves the right to revise this document for any reason,
       including but not limited to conformity with standards
       promulgated by various agencies, utilisation of advances in the
       state of the technical areas, or the reflection of changes in the
       design of any equipment, techniques, or procedures described or
       referred to herein.

       The product specifications and other technical or performance
       information contained herein are subject to change without
       notice. Updates of this document will be issued under the above
       NDA's.

       Nokia makes no representation or warranty, expressed or implied,
       with respect to the sufficiency, accuracy, or utility of any
       information or opinion contained herein. Nokia expressly advises
       that any use of for any purpose or reliance upon this technical
       reference is at the risk of the user and that Nokia shall not be
       liable for any damage or injury incurred by any person arising
       out of the sufficiency, accuracy, or utility of any information
       or opinion contained herein.

       This document is not to be construed as a suggestion to any
       manufacturer to modify or change any of its products, nor does
       this document represent any commitment by Nokia to sell or
       purchase any product. Nothing contained herein shall be construed
       as conferring by implication, estoppel, or otherwise any license
       or right under any patent, whether or not the use of any
       information herein necessarily employs an invention of any
       existing or later issued patent.

       Nokia reserves the right not to offer any or all of these
       products and to withdraw any or all of them at any future time.

       Copyright (C) 2023, Nokia. All Rights Reserved.";

    revision 2023-04-04 {
        description "Restrict the external authentication";
        reference "BBN-39109";
    }

    deviation "/nokia-aaa:users/nokia-aaa:user/nokia-aaa:authentication/nokia-aaa:ext-auth-enabled" {
	    description "Disable the external authentication on users";
        deviate not-supported;
    }

}
