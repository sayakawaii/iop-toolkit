module nokia-sdan-interface-dynamic-association-identities {
  yang-version 1.1;
  namespace "urn:bbf:yang:nokia-sdan-interface-dynamic-association-identities";
  prefix nokia-itf-dyn-id;

  organization
     "Nokia";
  contact
    "Comments or questions about this Nokia YANG module should be
     directed to <mailto:isam.yang@nokia.com>.";

  description
    "This module contains a collection of YANG definitions for
     supporting dynamic association of attributes with Interface
     
     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

  revision 2024-03-07 {
    description
      "Initial Revision";
    reference
      "Nokia specific";
  }

  identity association-origin-base {
    description
      "Base identity used to reflects the origin of the
       association with VLAN sub-interface";
  }

  identity statically-configured {
    base association-origin-base;
    description
      "The association is made by static configuration.";
  }

  identity dynamically-associated {
    base association-origin-base;
    description
      "The association is made dynamically through a control
       protocol";
  }

  identity dynamic-association-control-base {
    description
     "Determines the dynamic association of a forwarder and QoS
      policy profiles provided in a Access-accept
      or CoA-request message from a Radius server on the Interface.";
  }

  identity only-dynamic-association-allowed {
    base dynamic-association-control-base;
    description
     "If a forwarder and/or dynamic QoS policy profiles are received
      in an Access-accept or CoA-request message from a Radius server,
      there will be an attempt to apply these configurations.
      The configuration of static forwarder and static QoS policy
      profiles are not allowed on this entity.";
  }
}
