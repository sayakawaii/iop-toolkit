module nokia-ethmgnt-alarm-types {
     yang-version 1.1;
     namespace "https://www.nokia.com/Fixed-Networks/BBA/yang/nokia-ethmgnt-alarm-types";
     prefix ethmgnt-al;

     import nokia-base-alarm-types {
         prefix base-al;
     }

     organization
      "Nokia";

     contact
      "Comments or questions about this Nokia YANG module should be
       directed to <mailto:isam.yang@nokia.com>.";

     description
       "This module provides the details of supported ethernet management alarm types.

        This specification is published by Nokia under Non-Disclosure
        Agreement(s) (NDA) with specific parties and has to be considered
        as Confidential Information as defined in such NDA. Nokia
        reserves the right to revise this document for any reason,
        including but not limited to conformity with standards
        promulgated by various agencies, utilisation of advances in the
        state of the technical areas, or the reflection of changes in the
        design of any equipment, techniques, or procedures described or
        referred to herein.

        The product specifications and other technical or performance
        information contained herein are subject to change without
        notice. Updates of this document will be issued under the above
        NDA's.

        Nokia makes no representation or warranty, expressed or implied,
        with respect to the sufficiency, accuracy, or utility of any
        information or opinion contained herein. Nokia expressly advises
        that any use of for any purpose or reliance upon this technical
        reference is at the risk of the user and that Nokia shall not be
        liable for any damage or injury incurred by any person arising
        out of the sufficiency, accuracy, or utility of any information
        or opinion contained herein.

        This document is not to be construed as a suggestion to any
        manufacturer to modify or change any of its products, nor does
        this document represent any commitment by Nokia to sell or
        purchase any product. Nothing contained herein shall be construed
        as conferring by implication, estoppel, or otherwise any license
        or right under any patent, whether or not the use of any
        information herein necessarily employs an invention of any
        existing or later issued patent.

        Nokia reserves the right not to offer any or all of these
        products and to withdraw any or all of them at any future time.

        Copyright (C) 2017, Nokia. All Rights Reserved.";

     revision 2024-01-19 {
       description
         "Added backplane link failure alarm.";
       reference
         "Nokia specific";
     }

     revision 2021-02-11 {
       description
         "Rename yang with nokia prefix.
           - nokia-ethmgnt-alarm-types
         ";
       reference
         "Nokia specific";
     }

     revision 2017-12-12 {
      description
        "Ethernet management alarms";
      reference
        "Nokia specific";
     }

     identity ethsfp-alarms {
       base base-al:equipment-alarm;
       description
         "ethmgnt specific alarm type definitions";
     }

    identity eth-bp-alarms {
       base base-al:equipment-alarm;
       description
         "ethmgnt backplane alarm definition";
     }


/*
 *  nokia-alarms
 *  +-- equipment-alarm
 *         +--ethsfp-alarms

 *                |  +--los (concrete)
 */


// WORKAROUND ---- Seems that IETF standard yang model should define the alarm categories e.g. communications-alarm.
//            ---- current approach is to use the definition in nokia-alarm model because I could not find it in IETF

//Draft proposal for alarm identifiers for ethmgnt ----

     identity los {
       base ethsfp-alarms;
       description
			   "loss of synchronization";
     }

/*
*  nokia-alarms
*  +-- equipment-alarm
*         +--eth-bp-alarms
*                |  +--backplane-data-link-failure
*/

     identity backplane-data-link-failure {
       base eth-bp-alarms;
       description
          "Board backplane datalink failure";
     }



}
