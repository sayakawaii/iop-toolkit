module nokia-sdan-dhcpv4-client-simulator-common-dev {

  namespace "http://www.nokia.com/Fixed-Networks/BBA/yang/"
            + "nokia-sdan-dhcpv4-client-simulator-common-dev";

  prefix nokia-sdan-dhcpv4-client-simulator-common-dev;

  import nokia-sdan-dhcpv4-client-simulator {
    prefix dhcpv4-client-sim;
  }

  organization
    "Nokia";

  contact
    "Comments or questions about this Nokia YANG module should be
     directed to <mailto:isam.yang@nokia.com>.";

  description
    "This module contains a collection of YANG deviations on top
     of the NOKIA nokia-sdan-dhcpv4-client-simulator yang module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2022, Nokia. All Rights Reserved.";

   revision 2023-05-05 {
    description
      "Client mac validation done in main yang";
    reference
      "Nokia specific";
  }

  revision 2022-09-21 {
    description
      "Initial revision.";
    reference
      "Nokia specific";
  }

  deviation "/dhcpv4-client-sim:dhcpv4-client-simulator/dhcpv4-client-sim:session" {
    description
      "Atmost 10 DHCPv4 Client session simulation is allowed.";
    deviate add {
      max-elements 10;
    }
  }

  /** forbid setting client mac address as multicast address, broadcast address and full 0 mac. */
  deviation "/dhcpv4-client-sim:dhcpv4-client-simulator/dhcpv4-client-sim:session/dhcpv4-client-sim:start-client-session/dhcpv4-client-sim:input/dhcpv4-client-sim:client-mac" {
    deviate add {
      must "current() != '00:00:00:00:00:00'" {
        error-message "Cannot configure 00:00:00:00:00:00 as client mac address";
      }
    }
  }

}
