module nokia-bbf-qos-policing-qos-fiber-dev {

  namespace
    "http://www.nokia.com/Fixed-Networks/BBA/yang/nokia-bbf-qos-policing-qos-fiber-dev";

  prefix  nokia-bbf-qos-policing-qos-fiber-dev;

  import bbf-qos-classifiers {
    prefix bbf-qos-cls;
  }

  import bbf-qos-policing {
    prefix bbf-qos-plc;
  }

  import bbf-qos-rate-control {
    prefix bbf-qos-rc;
  }
  
  organization
    "Nokia";

  contact
    "isam.yang@nokia.com";

  description
    "This module contains a collection of YANG deviations on top 
     of standard for supporting BBF/bbf-qos-policies YANG module.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017-2018, Nokia. All Rights Reserved.";

  /* revision */
  revision 2025-05-06 {
    description
      "[BBN-9324 LLLT-A]: clear obseleted classify types so remove the unsupported node";
    reference
      "Nokia specific";
  }

  /* revision */
  revision 2025-01-06 {
    description
      "Split the minimum cir rule into other categories.";
    reference
      "Nokia specific";
  }
  
  revision 2022-12-29 {
    description
      "policing-profile size update to 1024";
    reference
      "Nokia specific";
  }

  revision 2022-11-29 {
    description
      "hierarchical-policing is not supported";
    reference
      "Nokia specific";
  }
    
  revision 2022-08-30 {
    description
      "remove not-supported deviation and replaced with disable feature";
    reference
      "Nokia specific";
  }

  revision 2018-09-06 {
    description
      "removed bbf-qos-filters filter-match restriction.";
    reference
      "Nokia specific";
  }

  revision 2018-06-04 {
    description
      "removed bbf-qos-filters max element restriction.";
    reference
      "Nokia specific";
  }

  revision 2018-02-02 {
    description
      "Initial revision.";
    reference
      "Nokia specific";
  }

  deviation "/bbf-qos-cls:classifiers/bbf-qos-cls:classifier-entry/bbf-qos-cls:filter-method/bbf-qos-cls:inline/bbf-qos-cls:match-criteria/bbf-qos-plc:pbit-marking-list"
  {
    deviate add {
       must "not(current()/../../bbf-qos-cls:classifier-action-entry-cfg/bbf-qos-cls:action-type = 'bbf-qos-rc:rate-limit-frames')"
       {
            error-message "If a classifier action is rate-limit-frames, the filter should be match-all!";
       }

       must "not(current()/../../bbf-qos-cls:classifier-action-entry-cfg/bbf-qos-cls:action-type = 'bbf-qos-cls:scheduling-traffic-class' and count(current()/../bbf-qos-plc:pbit-marking-list) > 1)"
       {
            error-message "If a classifier action is scheduling-traffic-class, inner and outer tag can't use pbit filter at the same time!";
       }
    }
  }

  deviation "/bbf-qos-cls:classifiers/bbf-qos-cls:classifier-entry/bbf-qos-cls:filter-method/bbf-qos-cls:inline/bbf-qos-cls:match-criteria/bbf-qos-plc:dei-marking-list"
  {
    deviate add {
       must "not(current()/../../bbf-qos-cls:classifier-action-entry-cfg/bbf-qos-cls:action-type = 'bbf-qos-rc:rate-limit-frames')"
       {
            error-message "If a classifier action is rate-limit-frames, the filter should be match-all!";
       }
    }
  }

  deviation "/bbf-qos-plc:policing-profiles/bbf-qos-plc:policing-profile/bbf-qos-plc:hierarchical-policing"
  {
    deviate not-supported;
  }

  deviation "/bbf-qos-plc:policing-profiles/bbf-qos-plc:policing-profile"
  {
    deviate add{
      max-elements 512;
    }
  }

  deviation "/bbf-qos-cls:classifiers/bbf-qos-cls:classifier-entry/bbf-qos-cls:classifier-action-entry-cfg/bbf-qos-cls:action-cfg-params/bbf-qos-plc:flow-color"
  {
    deviate not-supported;
  }

  deviation "/bbf-qos-cls:classifiers/bbf-qos-cls:classifier-entry/bbf-qos-cls:filter-method/bbf-qos-cls:inline/bbf-qos-cls:match-criteria/bbf-qos-plc:flow-color"
  {
    deviate not-supported;
  }
}
