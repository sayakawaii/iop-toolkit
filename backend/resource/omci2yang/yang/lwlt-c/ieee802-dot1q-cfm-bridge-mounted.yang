module ieee802-dot1q-cfm-bridge-mounted {
  yang-version 1.1;

  namespace "urn:ieee:std:802.1Q:yang:ieee802-dot1q-cfm-bridge-mounted";
  prefix "cfm-bridge-mounted";

  import ieee802-dot1q-cfm-mounted { prefix "dot1q-cfm-mounted"; }
  import ietf-interfaces-mounted { prefix "if-mounted"; }
  import ieee802-types { prefix "ieee"; }
  import ieee802-dot1q-cfm-types { prefix "cfm-types"; }
  import ieee802-dot1q-types { prefix "dot1q-types"; }
  import nokia-template-common {
    prefix template-common;
  }  


  import bbf-fiber-onu-emulated-mount {
     prefix onu;
  }
  organization
    "IEEE 802.1 Working Group";

  contact
    "WG-URL: http://www.ieee802.org/1/
    WG-EMail: stds-802-1-L@ieee.org

    Contact: IEEE 802.1 Working Group Chair
    Postal: C/O IEEE 802.1 Working Group
            IEEE Standards Association
            445 Hoes Lane
            Piscataway
            NJ 08854
            USA

    E-mail: STDS-802-1-L@IEEE.ORG";

  description
    "Connectivity Fault Management (CFM) comprises capabilities
    for detecting, verifying, and isolating connectivity failures
    in Virtual Bridged Local Area Networks. This module binds
    the CFM modules to an IEEE 802.1Q Bridge.";

  revision 2019-09-30 {
    description
      "Creation for Working Group review.";
    reference
      "IEEE Std 802.1Q-2018, Bridges and Bridged Networks.";
  }


  /* -------------------------------------------------
   * Grouping definitions used by 802.1Qcx YANG module
   * -------------------------------------------------
   */

  grouping service-id-grouping {
    description
      "The list of VIDs, the I-SID, the TE-SID, or the SEG-ID
      monitored by this MA, if present. In the case that a list
      of VIDs is specified, the first VID in the list is the MA's
      Primary VID (default none). The specification of I-SID is
      allowed only in the case of I- or B-components. The TE-SID
      is allowed only in the case that PBB-TE or SPBM is supported.
      The SEG-ID is allowed only in the case that IPS is supported.";
    choice service-id {
      description
        "The type of service identifier.";
      case vids {
        list vid {
          key "vlan-id";
          description "A list of VIDs associated with any MHF on the
            VID, always including that VID. The first VID is the
            MA's primary VID. List is empty if no primary VID
            specified";
          leaf vlan-id {
            type dot1q-types:vlanid;
            description
              "The 12-bit VLAN identifier.";
          }
        }
      }
      case isid {
        leaf isid {
          type uint32 {
            range "1..16777215";
          }
          description
            "24-bit I-SID identifier.";
        }
      }
      case tesid {
        leaf tesid {
          type uint32 {
            range "1..4294967295";
          }
          description
            "The tesid is used as a service selector for MAs that are
            present in Bridges that implement PBB-TE functionality.";
        }
      }
      case segid {
        leaf segid {
          type uint32 {
            range "1..4294967295";
          }
          description
            "The segid is used as a service selector for MAs that are
            present in Bridges that implement IPS functionality.";
        }
      }
      case path-tesid {
        leaf path-tesid {
          type uint32 {
            range "1..4294967295";
          }
          description
            "The path-tesid is used as a service selector for SPBM
            path MAs.";
        }
      }
      case group-isid {
        leaf group-isid {
          type uint32 {
            range "1..4294967295";
          }
          description
            "The group-isid is used as a service selector for SPBM
            group MAs.";
        }
      }
    }
  }

  /* -------------------------------------------------------------
   *  Augmentations of objects defined in generic CFM YANG module
   *  (ieee802-dot1q-cfm) and generic MEP YANG module
   *  (ieee802-dot1q-cfm-mep).
   * -------------------------------------------------------------
   */

  augment "/onu:onus/onu:onu/onu:root/dot1q-cfm-mounted:cfm" {
    when "derived-from-or-self(../../onu:usage, 'template-common:node-actual-usage') or "
       + "derived-from-or-self(../../onu:usage, 'template-common:node-from-template-usage')" {
     description
       "it should be a node-actual-usage or node-from-template-usage ONU";
    } 
    description
      "Augment the base/common CFM model with CFM Bridge
      specific attributes.";

    list cfm-stack {
      key "port md-level direction service-selector service-id";
      config false;
      description
        "The CFM Stack contains information about the Maintenance
        Points configured on a particular Bridge Port (or
        Aggregation Port). It contains all CFM Stack specific related
        configuration and operational data.

        Upon a restart of the system, the system SHALL, if necessary,
        change the value of this variable, and rearrange the
        cfm-stack, so that it indexes the entry in the
        interface table with the same value of interface-ref that it
        indexed before the system restart. If no such entry exists,
        then the system SHALL delete all entries in the
        cfm-stack with the interface index.";
      leaf port {
        type leafref { path '../../../if-mounted:interfaces/if-mounted:interface/if-mounted:name'; }
        description
          "An interface on which maintenance points might be
          configured. This object represents the Bridge Port or
          Aggregation Port on which MEPs or MHFs might be
          configured.";
        reference
          "12.14.2.1.2a of IEEE Std 802.1Q-2018";
      }
      leaf md-level {
        type cfm-types:md-level-type;
        description
          "The MD level of the maintenance point";
        reference
          "12.14.2.1.2b  of IEEE Std 802.1Q-2018";
      }
      leaf direction {
        type cfm-types:mp-direction-type;
        description
          "The direction in which the maintenance point faces on the
          Bridge Port.";
        reference
          "12.14.2.1.2c of IEEE Std 802.1Q-2018";
      }
      leaf service-selector {
        type cfm-types:service-selector-type;
        description
          "The type of the service selector";
      }
      leaf service-id {
        type cfm-types:service-selector-value-type;
        description
          "A VID, I-SID, Traffic Engineering service
          instance Identifier (TE-SID), or Segment Identifier
          (SEG-ID) associated with an MP, or 0, in the case that
          the MP is associated with no VID, I-SID, TE-SID, or SEG-ID.";
        reference
          "12.14.2.1.2d of IEEE Std 802.1Q-2018";
      }
      leaf maintenance-group-id {
        when '../maintenance-point = "mep"' {
          description
            "This should only exist if the configured
            maintenance point is a MEP (and not a MHF).";
        }
        type leafref {
          path '../../../dot1q-cfm-mounted:cfm/dot1q-cfm-mounted:maintenance-group'
             + '/dot1q-cfm-mounted:maintenance-group-id';
        }
        mandatory true;
        description
          "The maintenance group that the MEP is associated with. If
          the Maintenance Point is a MHF created due to an entry in
          the default-md-levels list, it has no associated
          maintenance group, and therefore this leaf is not present.";
      }
      leaf mep-id {
        when '../maintenance-point = "mep"' {
          description
            "This should only exist if the configured
            maintenance-point is a MEP.";
        }
        type leafref {
          path '../../../dot1q-cfm-mounted:cfm'
             + '/dot1q-cfm-mounted:maintenance-group'
             + '[dot1q-cfm-mounted:maintenance-group-id = current()'
             + '/../maintenance-group-id]'
             + '/dot1q-cfm-mounted:mep/dot1q-cfm-mounted:mep-id';
        }
        mandatory true;
        description
          "The MEP identifier if a MEP is configured. Does not exist
          if the maintenance point is a MHF.";
        reference
          "12.14.2.1.3d of IEEE Std 802.1Q-2018";
      }
      leaf md-id {
        when '../maintenance-point != "mep"' {
          description
            "This should only exist if the configured
            maintenance point is a MHF (and not a MEP).";
        }
        type leafref {
          path '../../../dot1q-cfm-mounted:cfm/dot1q-cfm-mounted:maintenance-domain'
            + '/dot1q-cfm-mounted:md-id';
        }
        description
          "The maintenance domain that the MHF is
          associated with.  If the MHF is
          created due to an entry in the default-md-levels list,
          it has no associated maintenance domain, and therefore this
          leaf is not present.";
      }
      leaf ma-id {
        when '../maintenance-point != "mep"' {
          description
            "This should only exist if the configured maintenance
            point is a MHF (and not a MEP), and it has a
            Maintenance Domain.";
        }
        type leafref {
          path '../../../dot1q-cfm-mounted:cfm'
            +'/dot1q-cfm-mounted:maintenance-domain'
            +'[dot1q-cfm-mounted:md-id = current()/../md-id]'
            +'/dot1q-cfm-mounted:maintenance-association/dot1q-cfm-mounted:ma-id';
        }
        description
          "The maintenance association that the MHF is associated
          with.  If the MHF is created due to an entry in the
          default-md-levels list, it has no associated maintenance
          association, and therefore this leaf is not present.";
      }
      leaf mac-address {
        type ieee:mac-address;
        mandatory true;
        description
          "The MAC address of the maintenance point.";
        reference
          "12.14.2.1.3e of IEEE Std 802.1Q-2018";
      }
      leaf maintenance-point {
        type cfm-types:mp-type;
        mandatory true;
        description
          "Indicates the type of maintenance point. That is whether a
          MEP or MHF.";
        reference
          "12.14.2.1.3a of IEEE Std 802.1Q-2018";
      }
    }  // cfm-stack

/**
    // To be confirmed and removed.

    list default-md-level {
      key "bridge-id component-id service-selector primary-service-id";
      description
        "For each bridge component, the Default MD Level Managed
        Object controls MHF creation for VIDs that are not attached
        to a specific Maintenance Association Managed Object, and
        Sender ID TLV transmission by those MHFs.

        For each Bridge Port, and for each VLAN ID whose data can
        pass through that Bridge Port, an entry in this table is
        used by the algorithm in subclause 22.2.3 only if there is no
        entry in the Maintenance Association table defining an MA
        for the same VLAN ID and MD Level as this table's entry, and
        on which MA an Up MEP is defined. If there exists such an
        MA, that MA's objects are used by the algorithm in
        subclause 22.2.3 in place of this table entry objects.

        The agent maintains the value of md-status to indicate
        whether this entry is overridden by an MA. When first
        initialized, the agent creates this table automatically with
        entries for all VLAN IDs, with the default values specified
        for each object. After this initialization, the writable
        objects in this table need to be persistent upon reboot or
        restart of a device.";
      leaf bridge-id {
        type bridge-ref;
        description
          "The reference to the IEEE 802.1Q Bridge associated with
          the CFM objects.";
      }
      leaf component-id {
        type leafref {
          path '/dot1q:bridges/dot1q:bridge'
            + '[dot1q:name = current()/../bridge-id]'
            + '/dot1q:component/dot1q:name';
        }
        description
          "The Bridge component within the system to which the
          information in this entry applies. If the system is not a
          Bridge, or if only one component is present in the Bridge,
          then this variable (index) MUST be equal to 1.";
        reference
          "12.3l of IEEE Std 802.1Q-2018";
      }
      leaf service-selector {
        type cfm-types:service-selector-type;
        description
          "The type of the service selector";
      }
      leaf primary-service-id {
        type cfm-types:service-selector-value-type;
        description
          "A vid or isid in an I or B component.";
        reference
          "12.14.3.1.2a of IEEE Std 802.1Q-2018";
      }
      container associated-service-ids {
        description
          "A list of VIDs associated with any MHF on the VID, always
          including that VID, or the Backbone-SID of the B-component
          or VIP-SID of the I-component associated with any MHF on
          the I-SID. The first VID is the MAs Primary VID.

          List is empty if no primary VID specified.";
        uses service-id-grouping;
        reference
          "12.14.3.1.3a of IEEE Std 802.1Q-2018";
      }
      leaf md-status {
        type boolean;
        config false;
        mandatory true;
        description
          "A Boolean value indicating whether this entry is in effect
          or has been overridden by the existence of a Maintenance
          Association managed object associated with the same VID or
          I-SID of I- or B-components and MD Level, and on which is
          configured an Up MEP. True if this Maintenance Domain
          managed object is in effect.";
        reference
          "12.14.3.1.3b of IEEE Std 802.1Q-2018";
      }
      leaf md-level {
        type cfm-types:md-level-type;
        mandatory true;
        description
          "A value indicating the MD Level at which MHFs are to be
          created, and Sender ID TLV transmission by those MHFs is to
          be controlled, for the VLAN to which this entry's objects
          apply.";
        reference
          "12.14.3.1.3c, 12.14.3.2.2b of IEEE Std 802.1Q-2018";
      }
      leaf mhf-creation {
        type cfm-types:mhf-creation-type;
        must '. != "mhf-defer"' {
          description
            "The value can not be mhf-defer. Must be one of mhf-none,
            mhf-default, or mfh-explicit.";
        }
        default "mhf-none";
        description
          "An enumerated value indicating whether the management
          entity can create MHFs for this VID(s) or I-SID(s) of I- or
          B-components.";
        reference
          "12.14.3.1.3d of IEEE Std 802.1Q-2018";

      }
      leaf id-permission {
        type cfm-types:sender-id-permission-type;
        must '. != "send-id-defer"' {
          description
            "The value can not be send-id-defer. Must be one of
            send-id-none, send-id-chassis, send-id-manage,
            send-id-chassis-manage.";
        }
        default "send-id-none";
        description
          "An enumerated value indicating what, if anything, is to be
          included in the Sender ID TLV transmitted by MPs configured
          in the Default Maintenance Domain.";
        reference
          "12.14.3.1.3e, 12.14.3.2.2a of IEEE Std 802.1Q-2018";
      }
    } // default-md-level

    list config-error {
      key "port service-selector service-id";
      config false;
      description
        "The CFM Configuration Error List table provides a list of
        Interfaces and VIDs that are incorrectly configured.";
      leaf port {
        type port-ref;
        description
          "The interface index of the interface (i.e., Bridge
          Port).

          Upon a restart of the system, the system SHALL, if
          necessary, change the value of this variable so that it
          indexes the entry in the interface table with the same
          value of the index that it indexed before the system
          restart. If no such entry exists, then the system SHALL
          delete any entries in config-error-list indexed by that
          interface-ref.";
        reference
          "12.14.4.1.2b of IEEE Std 802.1Q-2018";
      }
      leaf service-selector {
        type cfm-types:service-selector-type;
        description
          "The type of the service selector";
      }
      leaf service-id {
        type cfm-types:service-selector-value-type;
        description
          "A vid or isid in an I or B component.";
        reference
          "12.14.4.1.2a of IEEE Std 802.1Q-2018";
      }
      leaf error-type {
        type cfm-types:config-error-type;
        mandatory true;
        description
          "vector of Boolean error conditions from 22.2.4.";
        reference
          "12.14.4.1.3b of IEEE Std 802.1Q-2018";
      }
    } // config-error
*/

  }

} // ieee802-cfm-bridge
