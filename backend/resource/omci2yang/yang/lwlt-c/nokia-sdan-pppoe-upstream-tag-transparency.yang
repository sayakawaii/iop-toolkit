module nokia-sdan-pppoe-upstream-tag-transparency {
  yang-version 1.1;
  namespace "http://www.nokia.com/Fixed-Networks/BBA/yang/"
          + "nokia-sdan-pppoe-upstream-tag-transparency";
  prefix pppoe-upstream-tag-transparency;

  import bbf-pppoe-intermediate-agent {
    prefix bbf-pppoe-ia;
  }

  organization
    "Nokia";

  contact
    "Comments or questions about this Nokia YANG module should be
     directed to <mailto:isam.yang@nokia.com>.";

  description
    "This module contains a collection of YANG definitions for
     supporting Nokia specific requirements as applicable to its
     access network equipment.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2025, Nokia. All Rights Reserved.";

  revision 2025-07-23 {
    description
      "Initial revision of YANG model support configuration of
       upstream-tag-transparency.";
    reference
      "Nokia specific";
  }

  augment
    "/bbf-pppoe-ia:pppoe-profiles" +
    "/bbf-pppoe-ia:pppoe-profile" {
    description
      "Augments the configuration of the PPPoE relay profile with
       additional PPPoE upstream-tag-transparency parameter.";

    leaf upstream-tag-transparency {
      type empty;
      description
        "Configure upstream behavior to transparently forward
         the PPPoE packets received from the PPPoE Client with
         the vendor-specific tag.
         If this leaf is set, upstream PPPoE messages with the tag
         will be forwarded transparently.";
    }
  }
}
