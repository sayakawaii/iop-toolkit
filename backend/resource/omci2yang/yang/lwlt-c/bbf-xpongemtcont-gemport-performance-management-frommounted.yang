module bbf-xpongemtcont-gemport-performance-management-frommounted {
  yang-version 1.1;
  namespace "urn:bbf:yang:"
          + "bbf-xpongemtcont-gemport-performance-management-frommounted";
  prefix bbf-xpongemtcont-gemport-pm-frommounted;
  import bbf-fiber-onu-emulated-mount {
     prefix onu;
  }
  import bbf-xpongemtcont-frommounted {
    prefix bbf-xpongemtcont-frommounted;
  }
  organization
    "Broadband Forum <https://www.broadband-forum.org>
     Fiber Access Networks Work Area";
  contact
    "Comments or questions about this Broadband Forum YANG module
     should be directed to <mailto:info@broadband-forum.org>.
     Editor:      Joey Boyd, ADTRAN
     Editor:      Igor Ternovsky, Broadcom
     Editor:      Robert Peschi, Nokia
     WA Director: Marta Seda, Calix
     WA Director: Samuel Chen, Broadcom";
  description
    "This module contains a collection of YANG definitions for
     supporting the Broadband Forum requirements on management of
     ITU-T Passive Optical Network (PON) interfaces as defined in
     ITU-T G.984.x, G.987.x, ITU-T G.989.x and ITU-T G.9807.x. As
     such, this module is specific to access network equipment (e.g.,
     BBF-specified Access Nodes and FTTdp DPUs).
     Specifically, this module defines the management of performance
     monitoring of G-PON Encapsulation Method (GEM) ports.
     Copyright (c) 2018-2020, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-385i2; see
     the TR itself for full legal notices.";
  revision 2020-10-13 {
    description
      "Issue 2.
       * Approval Date:    2020-10-13.
       * Publication Date: 2020-10-13.";
    reference
      "TR-385i2: ITU-T PON YANG Modules
               <https://www.broadband-forum.org/technical/download/
                        TR-385_Issue-2.pdf>";
  }


  augment "/onu:onus/onu:onu/onu:fromroot/"
        + "bbf-xpongemtcont-frommounted:xpongemtcont/bbf-xpongemtcont-frommounted:gemports/bbf-xpongemtcont-frommounted:gemport" {
    description
      "Data nodes for the performance configuration parameters.";
    container performance {
      presence "performance";
      description
        "Performance parameters.";
      leaf enable {
        type boolean;
        description
          "If true, enables counting of performance statistics.
           Then performance statistics will be available in
           /xpongemtcont-state/gemports/gemport/performance.
           i.e. 15 minutes statistics and 24 hours statistics,
           and for both there are current statistics and history
           data.
           If false, then there are no performance statistics.";
      }
    }
  }
}
