module nokia-interface-speed-monitoring-eth-bp-sm-dev {

  namespace "http://www.nokia.com/Fixed-Networks/BBA/yang/"
          + "nokia-interface-speed-monitoring-eth-bp-sm-dev";

  prefix  nokia-interface-speed-monitoring-eth-bp-sm-dev;

  import ietf-interfaces {
      prefix if;
  }

  import nokia-interface-speed-monitoring {
      prefix nokia-itf-tm;
  }

  organization
    "Nokia";

  contact
    "isam.yang@nokia.com";

  description
    "The NOKIA ethernet YANG module supporting
     deviations on top of standard.";

  revision 2020-11-13 {
    description
      "move from eth-bp.";
    reference
      "TBD";
  }
  
  revision 2019-08-05 {
    description
      "Initial revision.";
    reference
      "TBD";
  }
  
  deviation "/if:interfaces/if:interface/nokia-itf-tm:speed-monitoring/nokia-itf-tm:enable" {
     deviate add{
        must "((current()/../../if:name != 'BP_Eth') or ((current()/../../if:name = 'BP_Eth') and (current() = 'false')))" {
                  error-message "Speed_monitoring Cannot Modified on BP_Eth Interface";
        }
     }
  }
  
}
