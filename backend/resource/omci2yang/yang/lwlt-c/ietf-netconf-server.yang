module ietf-netconf-server {
  yang-version 1.1;

  namespace "urn:ietf:params:xml:ns:yang:ietf-netconf-server";
  prefix "ncs";

  import ietf-yang-types {
    prefix yang;
    reference
      "RFC 6991: Common YANG Data Types";
  }

  import ietf-inet-types {
    prefix inet;
    reference 
      "RFC 6991: Common YANG Data Types";
  }

  import ietf-x509-cert-to-name {
    prefix x509c2n;
    reference
      "RFC 7407: A YANG Data Model for SNMP Configuration";
  }  

  import ietf-ssh-server {
    prefix ss;
    revision-date 2019-06-07; // stable grouping definitions
    reference
      "RFC YYYY: YANG Groupings for SSH Clients and SSH Servers";
  }

  import ietf-tls-server {
    prefix ts;
    // revision-date 2018-10-22; // stable grouping definitions
    reference
      "RFC ZZZZ: YANG Groupings for TLS Clients and TLS Servers";
  }

  organization
   "IETF NETCONF (Network Configuration) Working Group";

  contact
   "WG Web:   <http://datatracker.ietf.org/wg/netconf/>
    WG List:  <mailto:netconf@ietf.org>

    Author:   Kent Watsen
              <mailto:kwatsen@juniper.net>
              
    Author:   Gary Wu
              <mailto:garywu@cisco.com>

    Author:   Juergen Schoenwaelder
              <mailto:j.schoenwaelder@jacobs-university.de>";


  description
   "This module contains a collection of YANG definitions for
    configuring NETCONF servers.

    Copyright (c) 2017 IETF Trust and the persons identified as
    authors of the code. All rights reserved.

    Redistribution and use in source and binary forms, with or
    without modification, is permitted pursuant to, and subject
    to the license terms contained in, the Simplified BSD
    License set forth in Section 4.c of the IETF Trust's
    Legal Provisions Relating to IETF Documents
    (http://trustee.ietf.org/license-info).

    This version of this YANG module is part of RFC XXXX; see
    the RFC itself for full legal notices.";

  revision "2018-10-22" {
    description
     "Initial version";
    reference
     "RFC XXXX: NETCONF Client and Server Models";
  }


  // Features

  feature listen {
    description
     "The 'listen' feature indicates that the NETCONF server 
      supports opening a port to accept NETCONF client connections
      using at least one transport (e.g., SSH, TLS, etc.)."; 
  }

  feature ssh-listen {
    description
     "The 'ssh-listen' feature indicates that the NETCONF server 
      supports opening a port to accept NETCONF over SSH 
      client connections."; 
    reference
     "RFC 6242:
        Using the NETCONF Protocol over Secure Shell (SSH)";
  }

  feature tls-listen {
    description
     "The 'tls-listen' feature indicates that the NETCONF server 
      supports opening a port to accept NETCONF over TLS 
      client connections."; 
    reference
     "RFC 7589: Using the NETCONF Protocol over Transport
                Layer Security (TLS) with Mutual X.509
                Authentication";
  }

  feature call-home {
    description
     "The 'call-home' feature indicates that the NETCONF server
      supports initiating NETCONF call home connections to
      NETCONF clients using at least one transport (e.g., SSH,
      TLS, etc.).";
    reference
     "RFC 8071: NETCONF Call Home and RESTCONF Call Home";
  }

  feature ssh-call-home {
    description
     "The 'ssh-call-home' feature indicates that the NETCONF 
      server supports initiating a NETCONF over SSH call
      home connection to NETCONF clients.";
    reference
     "RFC 8071: NETCONF Call Home and RESTCONF Call Home";
  }

  feature tls-call-home {
    description
     "The 'tls-call-home' feature indicates that the NETCONF 
      server supports initiating a NETCONF over TLS call
      home connection to NETCONF clients.";
    reference
     "RFC 8071: NETCONF Call Home and RESTCONF Call Home";
  }


  // protocol accessible nodes

  container netconf-server {
    uses netconf-server-grouping;
    description
      "Top-level container for NETCONF server configuration.";
  }

  // reusable groupings

  grouping netconf-server-grouping {
    description
      "Top-level grouping for NETCONF server configuration.";
    container listen {
      if-feature listen;
      presence "Enables server to listen for TCP connections";
      description "Configures listen behavior";
      leaf idle-timeout {
        type uint16;
        units "seconds";
        default 3600; // one hour
        description
          "Specifies the maximum number of seconds that a NETCONF
           session may remain idle. A NETCONF session will be
           dropped if it is idle for an interval longer than this
           number of seconds.  If set to zero, then the server
           will never drop a session because it is idle.  Sessions
           that have a notification subscription active are never
           dropped.";
      }
      list endpoint {
        key name;
        min-elements 1;
        description
          "List of endpoints to listen for NETCONF connections.";
        leaf name {
          type string;
          description
            "An arbitrary name for the NETCONF listen endpoint.";
        }
        choice transport {
          mandatory true;
          description
            "Selects between available transports.";
          case ssh {
            if-feature ssh-listen;
            container ssh {
              description
                "SSH-specific listening configuration for inbound
                 connections.";
              leaf address {
                type inet:ip-address;
                mandatory true;
                description
                  "The IP address to listen on for incoming
                   connections.  The NETCONF server will listen
                   on all configured interfaces if no value is
                   specified.  INADDR_ANY (0.0.0.0) or INADDR6_ANY
                   (0:0:0:0:0:0:0:0 a.k.a. ::) MUST be used when
                   the server is to listen on all IPv4 or IPv6
                   addresses, respectively.";
              }
              leaf port {
                type inet:port-number;
                default 830;
                description
                 "The local port number to listen on.  If no value
                  is specified, the IANA-assigned port value for 
                  'netconf-ssh' (830) is used.";
              }
              uses ss:ssh-server-grouping;
            }
          }
          case tls {
            if-feature tls-listen;
            container tls {
              description
                "TLS-specific listening configuration for inbound
                 connections.";
              leaf address {
                type inet:ip-address;
                mandatory true;
                description
                  "The IP address to listen on for incoming
                   connections.  The NETCONF server will listen
                   on all configured interfaces if no value is
                   specified.  INADDR_ANY (0.0.0.0) or INADDR6_ANY
                   (0:0:0:0:0:0:0:0 a.k.a. ::) MUST be used when
                   the server is to listen on all IPv4 or IPv6
                   addresses, respectively.";
              }
              leaf port {
                type inet:port-number;
                default 6513;
                description
                 "The local port number to listen on.  If no value
                  is specified, the IANA-assigned port value for 
                  'netconf-tls' (6513) is used.";
              }
              uses ts:tls-server-grouping {
              refine "client-auth" {
                  must 'pinned-ca-certs or pinned-client-certs';
                  description
                    "NETCONF/TLS servers MUST validate client
                     certiticates.";
                }
  
                augment "client-auth" {
                  description
                    "Augments in the cert-to-name structure.";
                  container cert-maps {
                    uses x509c2n:cert-to-name;
                    description
                     "The cert-maps container is used by a TLS-
                      based NETCONF server to map the NETCONF
                      client's presented X.509 certificate to a
                      NETCONF username.  If no matching and valid
                      cert-to-name list entry can be found, then
                      the NETCONF server MUST close the connection,
                      and MUST NOT accept NETCONF messages over
                      it.";
                    reference
                      "RFC WWWW: NETCONF over TLS, Section 7";
                  }
                }
              }
            }
          }
        }
      }
    }

    container call-home {
      if-feature call-home;
      presence "Enables server to initiate TCP connections";
      description "Configures call-home behavior";
      list netconf-client {
        key name;
        min-elements 1;
        description
          "List of NETCONF clients the NETCONF server is to
           initiate call-home connections to in parallel.";
        leaf name {
          type string;
          description
            "An arbitrary name for the remote NETCONF client.";
        }
        container endpoints {
          description
            "Container for the list of endpoints.";
          list endpoint {
            key name;
            min-elements 1;
            ordered-by user;
            description
              "A non-empty user-ordered list of endpoints for this
               NETCONF server to try to connect to in sequence.  
               Defining more than one enables high-availability.";
            leaf name {
              type string;
              description
                "An arbitrary name for this endpoint.";
            }
            choice transport {
              mandatory true;
              description
                "Selects between available transports.";
              case ssh {
                if-feature ssh-call-home;
                container ssh {
                  description
                    "Specifies SSH-specific call-home transport
                     configuration.";
                  leaf address {
                    type inet:host;
                    mandatory true;
                    description
                     "The IP address or hostname of the endpoint.
                      If a domain name is configured, then the
                      DNS resolution should happen on each usage
                      attempt.  If the the DNS resolution results
                      in multiple IP addresses, the IP addresses
                      will be tried according to local preference
                      order until a connection has been established
                      or until all IP addresses have failed.";
                  }
                  leaf port {
                    type inet:port-number;
                    default 4334;
                    description
                     "The IP port for this endpoint. The NETCONF
                      server will use the IANA-assigned well-known
                      port for 'netconf-ch-ssh' (4334) if no value
                      is specified.";
                  }
                  uses ss:ssh-server-grouping;
                }
              }
              case tls {
                if-feature tls-call-home;
                container tls {
                  description
                    "Specifies TLS-specific call-home transport
                     configuration.";
                  leaf address {
                    type inet:host;
                    mandatory true;
                    description
                     "The IP address or hostname of the endpoint.
                      If a domain name is configured, then the
                      DNS resolution should happen on each usage
                      attempt.  If the the DNS resolution results
                      in multiple IP addresses, the IP addresses
                      will be tried according to local preference
                      order until a connection has been established
                      or until all IP addresses have failed.";
                  }
                  leaf port {
                    type inet:port-number;
                    default 4335;
                    description
                     "The IP port for this endpoint.  The NETCONF
                      server will use the IANA-assigned well-known
                      port for 'netconf-ch-tls' (4335) if no value
                      is specified.";
                  }
                  uses ts:tls-server-grouping {
   /*  This is temporarily removed as deletion of this constratin via deviation does not work,  */
   /*  and SW should be modified as this constraint should not be removed in future             */
   /*                 refine "client-auth" {                                                    */
   /*                  must 'pinned-ca-certs or pinned-client-certs';                           */
   /*                  description                                                              */
   /*                   "NETCONF/TLS servers MUST validate client                               */
   /*                    certiticates.";                                                        */
   /*                 }                                                                         */
                    augment "client-auth" {
                      description
                        "Augments in the cert-to-name structure.";
                      container cert-maps {
                        uses x509c2n:cert-to-name;
                        description
                         "The cert-maps container is used by a
                          TLS-based NETCONF server to map the
                          NETCONF client's presented X.509
                          certificate to a NETCONF username.  If
                          no matching and valid cert-to-name list
                          entry can be found, then the NETCONF
                          server MUST close the connection, and
                          MUST NOT accept NETCONF messages over
                          it.";
                        reference
                          "RFC WWWW: NETCONF over TLS, Section 7";
                      }
                    }
                  }
                }
              } // end tls
            } // end choice
          } // end endpoint
        }
        container connection-type {
          description
           "Indicates the kind of connection to use.";
          choice connection-type {
            mandatory true;
            description
              "Selects between available connection types.";
            case persistent-connection {
              container persistent {
                presence
                 "Indicates that a persistent connection is to be
                  maintained."; 
                description
                 "Maintain a persistent connection to the NETCONF 
                  client. If the connection goes down, immediately 
                  start trying to reconnect to it, using the 
                  reconnection strategy.
    
                  This connection type minimizes any NETCONF client
                  to NETCONF server data-transfer delay, albeit at 
                  the expense of holding resources longer.";
                container keep-alives {
                  description
                    "Configures the keep-alive policy, to
                     proactively test the aliveness of the SSH/TLS
                     client.  An unresponsive SSH/TLS client will
                     be dropped after approximately max-attempts *
                     max-wait seconds.";
                  reference
                    "RFC 8071: NETCONF Call Home and RESTCONF
                               Call Home, Section 4.1, item S7";
                  leaf max-wait {
                    type uint16 {
                      range "1..max";
                    }
                    units seconds;
                    default 30;
                    description
                     "Sets the amount of time in seconds after
                      which if no data has been received from
                      the SSH/TLS client, a SSH/TLS-level message
                      will be sent to test the aliveness of the
                      SSH/TLS client.";
                  }
                  leaf max-attempts {
                    type uint8;
                    default 3;
                    description
                     "Sets the maximum number of sequential keep-
                     alive messages that can fail to obtain a 
                     response from the SSH/TLS client before 
                     assuming the SSH/TLS client is no longer
                     alive.";
                  }
                }
              }
            }

            case periodic-connection {
              container periodic {
                presence
                 "Indicates that a periodic connection is to be
                  maintained."; 
                description
                 "Periodically connect to the NETCONF client.  The
                  NETCONF client should close the underlying TLS
                  connection upon completing planned activities.

                  This connection type increases resource
                  utilization, albeit with increased delay in
                  NETCONF client to NETCONF client interactions.";
                leaf period {
                  type uint16;
                  units "minutes";
                  default 60;
                  description
                    "Duration of time between periodic connections.";
                }
                leaf anchor-time {
                  type yang:date-and-time {
                    // constrained to minute-level granularity
                    pattern '\d{4}-\d{2}-\d{2}T\d{2}:\d{2}'
                            + '(Z|[\+\-]\d{2}:\d{2})';
                  }
                  description
                    "Designates a timestamp before or after which a
                     series of periodic connections are determined.
                     The periodic connections occur at a whole
                     multiple interval from the anchor time.  For
                     example, for an anchor time is 15 minutes past
                     midnight and a period interval of 24 hours, then
                     a periodic connection will occur 15 minutes past
                     midnight everyday.";
                }
                leaf idle-timeout {
                  type uint16;
                  units "seconds";
                  default 120; // two minutes
                  description
                    "Specifies the maximum number of seconds that
                     a NETCONF session may remain idle. A NETCONF 
                     session will be dropped if it is idle for an 
                     interval longer than this number of seconds.  
                     If set to zero, then the server will never
                     drop a session because it is idle.";
                }
              }
            }
          }
        }
        container reconnect-strategy {
          description
           "The reconnection strategy directs how a NETCONF server 
            reconnects to a NETCONF client, after discovering its
            connection to the client has dropped, even if due to a
            reboot.  The NETCONF server starts with the specified
            endpoint and tries to connect to it max-attempts times
            before trying the next endpoint in the list (round 
            robin).";
          leaf start-with {
            type enumeration {
              enum first-listed {
                description
                  "Indicates that reconnections should start with
                   the first endpoint listed.";
              }
              enum last-connected { 
                description
                  "Indicates that reconnections should start with
                   the endpoint last connected to.  If no previous
                   connection has ever been established, then the
                   first endpoint configured is used.   NETCONF 
                   servers SHOULD be able to remember the last 
                   endpoint connected to across reboots.";
              }
              enum random-selection { 
                description
                  "Indicates that reconnections should start with
                   a random endpoint.";
              }
            }
            default first-listed;
            description
             "Specifies which of the NETCONF client's endpoints
              the NETCONF server should start with when trying
              to connect to the NETCONF client.";
          }
          leaf max-attempts {
            type uint8 {
              range "1..max";
            }
            default 3;
            description
             "Specifies the number times the NETCONF server tries
              to connect to a specific endpoint before moving on
              to the next endpoint in the list (round robin).";
          }
        }
      }
    }
  }
}
