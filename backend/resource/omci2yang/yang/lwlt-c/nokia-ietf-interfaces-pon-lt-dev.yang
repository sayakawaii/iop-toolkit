module nokia-ietf-interfaces-pon-lt-dev {

  namespace "http://www.nokia.com/Fixed-Networks/BBA/yang/"
          + "nokia-ietf-interfaces-pon-lt-dev";

  prefix  ponltifdev;

  import ietf-interfaces {
      prefix if;
  }

  import iana-if-type {
    prefix ianaift;
  }

  import bbf-xpon-if-type {
    prefix bbf-xponift;
  }

  import bbf-if-type {
    prefix bbfift;
  }

  organization
    "Nokia";

  contact
    "Comments or questions about this Nokia YANG module should be 
     directed to <mailto:isam.yang@nokia.com>.";

  description
    "This module contains a collection of YANG definitions for 
     supporting Nokia specific requirements as applicable to its 
     access network equipment.
     
     Specifically, this module provides restrictions (=deviations) for
     the implementation in the ISAM 7363 MX.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2018, Nokia. All Rights Reserved.";

  revision 2025-06-25 {
    description
      "Add a deviation for supported interface types in interfaces-state.";
    reference
      "Nokia specific";
  }

  deviation '/if:interfaces/if:interface/if:type' {
    deviate add {
      must '(current() = "bbf-xponift:channel-group") or '
          +'(current() = "bbf-xponift:channel-partition") or '
          +'(current() = "bbf-xponift:channel-pair") or '
          +'(current() = "bbf-xponift:channel-termination") or '
          +'(current() = "bbf-xponift:v-ani") or '
          +'(current() = "bbf-xponift:olt-v-enet") or '
          +'(current() = "bbfift:vlan-sub-interface") or '
          +'(current() = "bbfift:l2-termination") or '
          +'(current() = "ianaift:ethernetCsmacd") or '
          +'(current() = "ianaift:ipForward")' {
        error-message "This interface type is not supported.";

        description
          "Restricts the set of supported interface types.";
      }
    }
  }

  deviation '/if:interfaces-state/if:interface/if:type' {
    deviate add {
      must '(current() = "bbf-xponift:channel-group") or '
          +'(current() = "bbf-xponift:channel-partition") or '
          +'(current() = "bbf-xponift:channel-pair") or '
          +'(current() = "bbf-xponift:channel-termination") or '
          +'(current() = "bbf-xponift:v-ani") or '
          +'(current() = "bbf-xponift:olt-v-enet") or '
          +'(current() = "bbfift:vlan-sub-interface") or '
          +'(current() = "bbfift:l2-termination") or '
          +'(current() = "ianaift:ethernetCsmacd") or '
          +'(current() = "ianaift:ipForward")' {
        error-message "This interface type is not supported.";

        description
          "Restricts the set of supported interface types.";
      }
    }
  }
}
