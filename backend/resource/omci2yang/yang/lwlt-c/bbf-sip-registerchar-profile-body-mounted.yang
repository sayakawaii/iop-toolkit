submodule bbf-sip-registerchar-profile-body-mounted {
  yang-version 1.1;
  belongs-to bbf-sip-voip-mounted  {
    prefix bbf-sip-voip-mounted;
  }
  
  import ietf-inet-types {
	prefix inet;
	reference
    		"RFC 6991: Common YANG Data Types.";
  }

  import bbf-yang-types {
 	prefix bbf-yang;
  }
   
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains the YANG definitions for managing the 
	 register characteristics.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2020-03-06 {
    description
      "Initial revision.
       * Approval Date:    see revision date above.
       * Publication Date: 2020-03-06.";
    reference
      " ";
  } 
  
  grouping sip-registerchar-profile-body {
	description
	  "Defines the SIP register method properties profile.";
	leaf register-uri {
      type inet:uri;  
      description
	    "The register URI to be used by all SIP terminations 
		 associated with a particular voip access gateway.";
    }
	leaf re-register-interval {
 	  type union {
      	type uint32 {range "60..86400";}
      	type enumeration {
          enum disabled {
	  	    description
        	  "Indicates that re-registration is disabled.
	  	       When re-registration is disabled, it means that a SIP 
	  	       termination does not refresh its	initial registration
	  	       even not if the registrar had specified an expiry 
			   interval.";
	  	  }
	  	}
	  }		
	  units seconds;
	  default 3600;		
	  description
	  	"The sip re-register Interval.";
	}
	leaf re-register-precursory-start-time {
 	  type union {
      	type uint32 {range "32..86400";}
      	type enumeration {
          enum disabled {
	  	    description
        	  "Indicates that re-registration precursory-start-time
			   is disabled.	It must be set to disabled when 
	  	       the sip-reregister-interval is set to disabled.";
	  	  }
	  	}
	  }		
	  units seconds;
	  default 600;	  
	  description
	  	"The sip re-register precursory start time i.e.
	  	 The number of seconds prior to registration
	  	 expiry at which the SIP UA sends a re-register 
	  	 request.
	  	 The time to send the re-registration request is
	  	 defined as follows :
	  	 In case the registration interval expiry > 
	  	 2* sip-reregister-precursory-start-time then
	  	 sip-reregister-precursory-start-time seconds 
	  	 prior to the expiry of the registration period
	  	 i.e at [register interval expiry minus the 
	  	 sip-reregister-precursory-start-time].
	  	 Otherwise:  the re-register message is sent at 
	  	 [registration interval * 0.5].";
	}
// BBOG make name consistent with other re-register-xxx names
	leaf re-register-min-precursory-start-time {
	  type bbf-yang:percent;
	  units "1 percent";
	  default 50;		
	  description
	  	"The sip re-register minimum precursory start 
	  	time i.e. the time expressed as a percentage
	  	prior to the expiry of the re-register period 
	  	that must not be exceeded to send the
	  	re-register request.";
	}
	leaf register-retry-interval {
	  type union {
      	type uint32 {range "30..86400";}
      	type enumeration {
          enum disabled {
	  	    description
        	  "Indicates that the SIP register retry is disabled.";
	  	  }
	  	}
	  }		
	  units seconds;
	  default 60;	  
	  description
	  	"The sip register retry interval (In case of 
	  	 register failure).
	  	 The registration retry can be disabled.";
	}
	leaf register-dispersion-interval {
	  type uint16 {range "100..32000";}
	  units "1 millisecond";
	  default 500;	  
	  description
	  	"The time interval between subsequent the 
	  	 initiation of 2 subsequent SIP register requests.";
	}	
  } 
}
