module nokia-qos-queue-monitoring-qos-fiber-dev {

  namespace
    "http://www.nokia.com/Fixed-Networks/BBA/yang/nokia-qos-queue-monitoring-qos-fiber-dev";

  prefix  nokia-qos-queue-monitoring-qos-fiber-dev;

  import bbf-qos-traffic-mngt {
    prefix bbf-qos-tm;
  }

  import ietf-interfaces {
    prefix if;
  }

  import nokia-qos-queue-monitoring{
    prefix nokia-queue-mon;
  }

  organization
    "Nokia";

  contact
    "isam.yang@nokia.com";

  description
    "This module contains a collection of YANG deviations on top
     of standard for supporting BBF/bbf-qos-traffic-mgnt YANG module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2017-2018, Nokia. All Rights Reserved.";

  /* revision */

  revision 2022-12-12 {
    description
      "Not supported deviation is added for discontinuity-time leaf.";
    reference
      "Nokia specific";
  }

  revision 2021-02-26 {
    description
      "Initial revision.";
    reference
      "Nokia specific";
  }

  deviation "/if:interfaces/if:interface/bbf-qos-tm:tm-root/bbf-qos-tm:children-type/bbf-qos-tm:queues/nokia-queue-mon:queue-monitoring"{
    deviate add {
       must "current()/nokia-queue-mon:enable-performance = current()/nokia-queue-mon:enable-statistics" {
         error-message "enable-performance must be same with enable-statistics";
       }
    }
  }

  deviation "/if:interfaces-state/if:interface/nokia-queue-mon:tm-root/nokia-queue-mon:discontinuity-time" {
       deviate not-supported;
  }
}
