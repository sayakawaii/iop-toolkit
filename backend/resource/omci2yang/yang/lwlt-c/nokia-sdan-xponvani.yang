module nokia-sdan-xponvani{
 yang-version 1.1;
 namespace "urn:broadband-forum-org:yang:nokia-sdan-xponvani";

prefix nokia-sdan-xponvani;

import bbf-xponvani{
    prefix bbf-xponvani;
}

import ietf-interfaces {
    prefix if;
  }

import nokia-sdan-hspon-types {
    prefix nokia-sdan-hspon-types;
}

organization
  "Nokia";

contact
  "Comments or questions about this Nokia YANG module should be
  directed to <mailto:isam.yang@nokia.com>.";

description
  "This specification is published by Nokia under Non-Disclosure
  Agreement(s) (NDA) with specific parties and has to be considered
  as Confidential Information as defined in such NDA. Nokia reserves
  the right to revise this document for any reason, including but
  not limited to conformity with standards promulgated by various
  agencies, utilization of advances in the state of the technical
  areas, or the reflection of changes in the design of any
  equipment, techniques, or procedures described or referred to
  herein.

  The product specifications and other technical or performance
  information contained herein are subject to change without notice.
  Updates of this document will be issued under the above NDA's.

  Nokia makes no representation or warranty, expressed or implied,
  with respect to the sufficiency, accuracy, or utility of any
  information or opinion contained herein. Nokia expressly advises
  that any use of for any purpose or reliance upon this technical
  reference is at the risk of the user and that Nokia shall not be
  liable for any damage or injury incurred by any person arising out
  of the sufficiency, accuracy, or utility of any information or
  opinion contained herein.

  This document is not to be construed as a suggestion to any
  manufacturer to modify or change any of its products, nor does
  this document represent any commitment by Nokia to sell or
  purchase any product. Nothing contained herein shall be construed
  as conferring by implication, estoppel, or otherwise any license
  or right under any patent, whether or not the use of any
  information herein necessarily employs an invention of any
  existing or later issued patent.

  Nokia reserves the right not to offer any or all of these products
  and to withdraw any or all of them at any future time.

  Copyright (C) 2022, Nokia. All Rights Reserved";

revision 2022-04-09 {
  description
    "Initial revision.";
  reference
    "TBD";
}
 
  augment '/if:interfaces/if:interface/bbf-xponvani:v-ani' {
    description "augment v-ani";
    container hs-pon-fec-type-selection {
      presence
        "When configured this container gives the possibility
         to configure the type of upstream FEC to be used for HS-PON.";
      description "hs-pon-fec-type-selection";
      leaf upstream-fec-type {
        type identityref {
          base nokia-sdan-hspon-types:fec-type-base;
        }
        default "nokia-sdan-hspon-types:fec-type-system-selected";
        description
          "Used to select the type of FEC in Upstream direction for this specific ONU.";
      }
    }
  } 
}
