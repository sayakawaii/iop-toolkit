module nokia-bbf-xpon-performance-management-common-dev {
  yang-version 1.1;

  namespace "http://www.nokia.com/Fixed-Networks/BBA/yang/"
          + "nokia-bbf-xpon-performance-management-common-dev";

  prefix  nokia-bbf-xpon-pm-common-dev;


  import bbf-xpon-performance-management {
    prefix "bbf-xpon-pm";
  }

  import bbf-interfaces-performance-management {
    prefix "bbf-if-pm";
  }

  import ietf-interfaces {
    prefix "if";
  }

  organization  
    "Nokia";
    
  contact 
    "Comments or questions about this Nokia YANG module should be 
     directed to <mailto:isam.yang@nokia.com>.";
    
  description 
    "The NOKIA BBF/xPON performance managment YANG module supporting 
     deviations on top of standard.
    This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2022, Nokia. All Rights Reserved."; 



/* revision */

   revision 2026-04-15 {
    description
      "Adding fec-seconds as not supported parameters.";
    reference
      "Nokia specific";
   }

   revision 2025-09-07 {
    description
      "Initial version.
       * NOKIA deviations for bbf-xpon-performance-management module revision 2020-10-13.
       * Deviations ploam counters not supported are removed.";
    reference
      "Nokia specific";
  }

  revision 2024-05-09 {
    description
      "Add not supported parameters.";
    reference
      "Nokia specific";
  }

  revision 2022-12-05 {
    description
      "Included deviations.
       * NOKIA deviations for bbf-xpon-performance-management module revision 2020-10-13.
       * Deviations are related to restricted functional behavior.";
    reference
      "Nokia specific"; 
  }   
 
  revision 2022-12-01 {
    description
      "Initial version.
       * NOKIA deviations for bbf-xpon-performance-management module revision 2020-10-13.
       * Deviations are related to restricted functional behavior.";
    reference
      "Nokia specific"; 
  }  

  revision 2022-08-26 {
    description
      "Initial version.
       * NOKIA deviations for bbf-xpon-performance-management module revision 2020-10-13.
       * Deviations ploam counters are not supported.";
    reference
      "Nokia specific"; 
  }

  revision 2022-07-05 {
    description
      "Initial version.
       * NOKIA deviations for bbf-xpon-performance-management module revision 2020-10-13.
       * Deviations are related to restricted functional behavior.";
    reference
      "Nokia specific"; 
  }  

/*-------- not-supported deviations 15min xpon ploam -------*/

// not supported current xpon ploam

  deviation "/if:interfaces-state/if:interface/bbf-if-pm:performance/bbf-if-pm:intervals-15min/bbf-if-pm:current/bbf-xpon-pm:xpon/bbf-xpon-pm:ploam/bbf-xpon-pm:calibration-request" {
    deviate not-supported;
  }

  deviation "/if:interfaces-state/if:interface/bbf-if-pm:performance/bbf-if-pm:intervals-15min/bbf-if-pm:current/bbf-xpon-pm:xpon/bbf-xpon-pm:ploam/bbf-xpon-pm:power-inquire" {
    deviate not-supported;
  }

  deviation "/if:interfaces-state/if:interface/bbf-if-pm:performance/bbf-if-pm:intervals-15min/bbf-if-pm:current/bbf-xpon-pm:xpon/bbf-xpon-pm:ploam/bbf-xpon-pm:reboot-onu" {
    deviate not-supported;
  }

  deviation "/if:interfaces-state/if:interface/bbf-if-pm:performance/bbf-if-pm:intervals-15min/bbf-if-pm:current/bbf-xpon-pm:xpon/bbf-xpon-pm:ploam/bbf-xpon-pm:bonded-channel-status" {
    deviate not-supported;
  }

  deviation "/if:interfaces-state/if:interface/bbf-if-pm:performance/bbf-if-pm:intervals-15min/bbf-if-pm:current/bbf-xpon-pm:xpon/bbf-xpon-pm:ploam/bbf-xpon-pm:get-set-capabilities" {
    deviate not-supported;
  }

  deviation "/if:interfaces-state/if:interface/bbf-if-pm:performance/bbf-if-pm:intervals-15min/bbf-if-pm:current/bbf-xpon-pm:xpon/bbf-xpon-pm:ploam/bbf-xpon-pm:dying-gasps" {
    deviate not-supported;
  }

  deviation "/if:interfaces-state/if:interface/bbf-if-pm:performance/bbf-if-pm:intervals-15min/bbf-if-pm:current/bbf-xpon-pm:xpon/bbf-xpon-pm:ploam/bbf-xpon-pm:mic-errors" {
    deviate not-supported;
  }

  deviation "/if:interfaces-state/if:interface/bbf-if-pm:performance/bbf-if-pm:intervals-15min/bbf-if-pm:current/bbf-xpon-pm:xpon/bbf-xpon-pm:ploam/bbf-xpon-pm:sn-grants" {
    deviate not-supported;
  }

  deviation "/if:interfaces-state/if:interface/bbf-if-pm:performance/bbf-if-pm:intervals-15min/bbf-if-pm:current/bbf-xpon-pm:xpon/bbf-xpon-pm:ploam/bbf-xpon-pm:timeouts" {
    deviate not-supported;
  }

//  not suppored current downstream ploam                 

  deviation "/if:interfaces-state/if:interface/bbf-if-pm:performance/bbf-if-pm:intervals-15min/bbf-if-pm:current/bbf-xpon-pm:xpon/bbf-xpon-pm:ploam/bbf-xpon-pm:downstream-messages/bbf-xpon-pm:adjust-tx-wavelength" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:assign-alloc-id" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:assign-onu-id" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:burst-profile" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:channel-profile" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:deactivate-onu-id" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:disable-serial-number" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:key-control" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:protect-control" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:request-registration" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:sleep-allow" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:system-profile" {
    deviate not-supported;
  }

  deviation "/if:interfaces-state/if:interface/bbf-if-pm:performance/bbf-if-pm:intervals-15min/bbf-if-pm:current/bbf-xpon-pm:xpon/bbf-xpon-pm:ploam/bbf-xpon-pm:downstream-messages/bbf-xpon-pm:tuning-control" {
    deviate not-supported;
  }

//  not suppored current upstream ploam                 

  deviation "/if:interfaces-state/if:interface/bbf-if-pm:performance/bbf-if-pm:intervals-15min/bbf-if-pm:current/bbf-xpon-pm:xpon/bbf-xpon-pm:ploam/bbf-xpon-pm:upstream-messages/bbf-xpon-pm:acknowledgement" {
    deviate not-supported;
  }

  deviation "/if:interfaces-state/if:interface/bbf-if-pm:performance/bbf-if-pm:intervals-15min/bbf-if-pm:current/bbf-xpon-pm:xpon/bbf-xpon-pm:ploam/bbf-xpon-pm:upstream-messages/bbf-xpon-pm:key-report" {
    deviate not-supported;
  }

  deviation "/if:interfaces-state/if:interface/bbf-if-pm:performance/bbf-if-pm:intervals-15min/bbf-if-pm:current/bbf-xpon-pm:xpon/bbf-xpon-pm:ploam/bbf-xpon-pm:upstream-messages/bbf-xpon-pm:power-consumption-report" {
    deviate not-supported;
  }

  deviation "/if:interfaces-state/if:interface/bbf-if-pm:performance/bbf-if-pm:intervals-15min/bbf-if-pm:current/bbf-xpon-pm:xpon/bbf-xpon-pm:ploam/bbf-xpon-pm:upstream-messages/bbf-xpon-pm:bonded-channel-rsp" {
    deviate not-supported;
  }

  deviation "/if:interfaces-state/if:interface/bbf-if-pm:performance/bbf-if-pm:intervals-15min/bbf-if-pm:current/bbf-xpon-pm:xpon/bbf-xpon-pm:ploam/bbf-xpon-pm:upstream-messages/bbf-xpon-pm:onu-capabilities" {
    deviate not-supported;
  }

  deviation "/if:interfaces-state/if:interface/bbf-if-pm:performance/bbf-if-pm:intervals-15min/bbf-if-pm:current/bbf-xpon-pm:xpon/bbf-xpon-pm:ploam/bbf-xpon-pm:upstream-messages/bbf-xpon-pm:registration" {
    deviate not-supported;
  }

  deviation "/if:interfaces-state/if:interface/bbf-if-pm:performance/bbf-if-pm:intervals-15min/bbf-if-pm:current/bbf-xpon-pm:xpon/bbf-xpon-pm:ploam/bbf-xpon-pm:upstream-messages/bbf-xpon-pm:serial-number-onu" {
    deviate not-supported;
  }

  deviation "/if:interfaces-state/if:interface/bbf-if-pm:performance/bbf-if-pm:intervals-15min/bbf-if-pm:current/bbf-xpon-pm:xpon/bbf-xpon-pm:ploam/bbf-xpon-pm:upstream-messages/bbf-xpon-pm:sleep-request" {
    deviate not-supported;
  }

  deviation "/if:interfaces-state/if:interface/bbf-if-pm:performance/bbf-if-pm:intervals-15min/bbf-if-pm:current/bbf-xpon-pm:xpon/bbf-xpon-pm:ploam/bbf-xpon-pm:upstream-messages/bbf-xpon-pm:tuning-response" {
    deviate not-supported;
  }

// not supported history xpon ploam

  deviation "/if:interfaces-state/if:interface/bbf-if-pm:performance/bbf-if-pm:intervals-15min/bbf-if-pm:history/bbf-xpon-pm:xpon/bbf-xpon-pm:ploam/bbf-xpon-pm:calibration-request" {
    deviate not-supported;
  }

  deviation "/if:interfaces-state/if:interface/bbf-if-pm:performance/bbf-if-pm:intervals-15min/bbf-if-pm:history/bbf-xpon-pm:xpon/bbf-xpon-pm:ploam/bbf-xpon-pm:power-inquire" {
    deviate not-supported;
  }

  deviation "/if:interfaces-state/if:interface/bbf-if-pm:performance/bbf-if-pm:intervals-15min/bbf-if-pm:history/bbf-xpon-pm:xpon/bbf-xpon-pm:ploam/bbf-xpon-pm:reboot-onu" {
    deviate not-supported;
  }

  deviation "/if:interfaces-state/if:interface/bbf-if-pm:performance/bbf-if-pm:intervals-15min/bbf-if-pm:history/bbf-xpon-pm:xpon/bbf-xpon-pm:ploam/bbf-xpon-pm:bonded-channel-status" {
    deviate not-supported;
  }

  deviation "/if:interfaces-state/if:interface/bbf-if-pm:performance/bbf-if-pm:intervals-15min/bbf-if-pm:history/bbf-xpon-pm:xpon/bbf-xpon-pm:ploam/bbf-xpon-pm:get-set-capabilities" {
    deviate not-supported;
  }

  deviation "/if:interfaces-state/if:interface/bbf-if-pm:performance/bbf-if-pm:intervals-15min/bbf-if-pm:history/bbf-xpon-pm:xpon/bbf-xpon-pm:ploam/bbf-xpon-pm:dying-gasps" {
    deviate not-supported;
  }

  deviation "/if:interfaces-state/if:interface/bbf-if-pm:performance/bbf-if-pm:intervals-15min/bbf-if-pm:history/bbf-xpon-pm:xpon/bbf-xpon-pm:ploam/bbf-xpon-pm:mic-errors" {
    deviate not-supported;
  }

  deviation "/if:interfaces-state/if:interface/bbf-if-pm:performance/bbf-if-pm:intervals-15min/bbf-if-pm:history/bbf-xpon-pm:xpon/bbf-xpon-pm:ploam/bbf-xpon-pm:sn-grants" {
    deviate not-supported;
  }

  deviation "/if:interfaces-state/if:interface/bbf-if-pm:performance/bbf-if-pm:intervals-15min/bbf-if-pm:history/bbf-xpon-pm:xpon/bbf-xpon-pm:ploam/bbf-xpon-pm:timeouts" {
    deviate not-supported;
  }

//  not suppored history downstream ploam                 

  deviation "/if:interfaces-state/if:interface/bbf-if-pm:performance/bbf-if-pm:intervals-15min/bbf-if-pm:history/bbf-xpon-pm:xpon/bbf-xpon-pm:ploam/bbf-xpon-pm:downstream-messages/bbf-xpon-pm:adjust-tx-wavelength" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:assign-alloc-id" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:assign-onu-id" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:burst-profile" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:channel-profile" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:deactivate-onu-id" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:disable-serial-number" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:key-control" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:protect-control" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:request-registration" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:sleep-allow" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:system-profile" {
    deviate not-supported;
  }

  deviation "/if:interfaces-state/if:interface/bbf-if-pm:performance/bbf-if-pm:intervals-15min/bbf-if-pm:history/bbf-xpon-pm:xpon/bbf-xpon-pm:ploam/bbf-xpon-pm:downstream-messages/bbf-xpon-pm:tuning-control" {
    deviate not-supported;
  }

//  not suppored history upstream ploam                 

  deviation "/if:interfaces-state/if:interface/bbf-if-pm:performance/bbf-if-pm:intervals-15min/bbf-if-pm:history/bbf-xpon-pm:xpon/bbf-xpon-pm:ploam/bbf-xpon-pm:upstream-messages/bbf-xpon-pm:acknowledgement" {
    deviate not-supported;
  }

  deviation "/if:interfaces-state/if:interface/bbf-if-pm:performance/bbf-if-pm:intervals-15min/bbf-if-pm:history/bbf-xpon-pm:xpon/bbf-xpon-pm:ploam/bbf-xpon-pm:upstream-messages/bbf-xpon-pm:key-report" {
    deviate not-supported;
  }

  deviation "/if:interfaces-state/if:interface/bbf-if-pm:performance/bbf-if-pm:intervals-15min/bbf-if-pm:history/bbf-xpon-pm:xpon/bbf-xpon-pm:ploam/bbf-xpon-pm:upstream-messages/bbf-xpon-pm:power-consumption-report" {
    deviate not-supported;
  }

  deviation "/if:interfaces-state/if:interface/bbf-if-pm:performance/bbf-if-pm:intervals-15min/bbf-if-pm:history/bbf-xpon-pm:xpon/bbf-xpon-pm:ploam/bbf-xpon-pm:upstream-messages/bbf-xpon-pm:bonded-channel-rsp" {
    deviate not-supported;
  }

  deviation "/if:interfaces-state/if:interface/bbf-if-pm:performance/bbf-if-pm:intervals-15min/bbf-if-pm:history/bbf-xpon-pm:xpon/bbf-xpon-pm:ploam/bbf-xpon-pm:upstream-messages/bbf-xpon-pm:onu-capabilities" {
    deviate not-supported;
  }

  deviation "/if:interfaces-state/if:interface/bbf-if-pm:performance/bbf-if-pm:intervals-15min/bbf-if-pm:history/bbf-xpon-pm:xpon/bbf-xpon-pm:ploam/bbf-xpon-pm:upstream-messages/bbf-xpon-pm:registration" {
    deviate not-supported;
  }

  deviation "/if:interfaces-state/if:interface/bbf-if-pm:performance/bbf-if-pm:intervals-15min/bbf-if-pm:history/bbf-xpon-pm:xpon/bbf-xpon-pm:ploam/bbf-xpon-pm:upstream-messages/bbf-xpon-pm:serial-number-onu" {
    deviate not-supported;
  }

  deviation "/if:interfaces-state/if:interface/bbf-if-pm:performance/bbf-if-pm:intervals-15min/bbf-if-pm:history/bbf-xpon-pm:xpon/bbf-xpon-pm:ploam/bbf-xpon-pm:upstream-messages/bbf-xpon-pm:sleep-request" {
    deviate not-supported;
  }

  deviation "/if:interfaces-state/if:interface/bbf-if-pm:performance/bbf-if-pm:intervals-15min/bbf-if-pm:history/bbf-xpon-pm:xpon/bbf-xpon-pm:ploam/bbf-xpon-pm:upstream-messages/bbf-xpon-pm:tuning-response" {
    deviate not-supported;
  }




// Deviations for bbf-xpon-pm:phy

  deviation "/if:interfaces-state/if:interface/bbf-if-pm:performance/bbf-if-pm:intervals-15min/bbf-if-pm:current/bbf-xpon-pm:xpon/bbf-xpon-pm:phy/bbf-xpon-pm:psbd-hec-errors" {
    deviate not-supported;
  }

  deviation "/if:interfaces-state/if:interface/bbf-if-pm:performance/bbf-if-pm:intervals-15min/bbf-if-pm:current/bbf-xpon-pm:xpon/bbf-xpon-pm:phy/bbf-xpon-pm:fs-hec-errors" {
    deviate not-supported;
  }

  deviation "/if:interfaces-state/if:interface/bbf-if-pm:performance/bbf-if-pm:intervals-15min/bbf-if-pm:current/bbf-xpon-pm:xpon/bbf-xpon-pm:phy/bbf-xpon-pm:unknown-profiles" {
    deviate not-supported;
  }

  deviation "/if:interfaces-state/if:interface/bbf-if-pm:performance/bbf-if-pm:intervals-15min/bbf-if-pm:current/bbf-xpon-pm:xpon/bbf-xpon-pm:phy/bbf-xpon-pm:fec-seconds" {
    deviate not-supported;
  }

// Deviations for bbf-xpon-pm:lods

  deviation "/if:interfaces-state/if:interface/bbf-if-pm:performance/bbf-if-pm:intervals-15min/bbf-if-pm:current/bbf-xpon-pm:xpon/bbf-xpon-pm:lods" {
    deviate not-supported;
  }

// Deviations for bbf-xpon-pm:gemports

  deviation "/if:interfaces-state/if:interface/bbf-if-pm:performance/bbf-if-pm:intervals-15min/bbf-if-pm:current/bbf-xpon-pm:xpon/bbf-xpon-pm:gemport" {
    deviate not-supported;
  }

// Deviations for bbf-xpon-pm:utilization

  deviation "/if:interfaces-state/if:interface/bbf-if-pm:performance/bbf-if-pm:intervals-15min/bbf-if-pm:current/bbf-xpon-pm:xpon/bbf-xpon-pm:utilization" {
    deviate not-supported;
  }

// Deviations for bbf-xpon-pm:activation

  deviation "/if:interfaces-state/if:interface/bbf-if-pm:performance/bbf-if-pm:intervals-15min/bbf-if-pm:current/bbf-xpon-pm:xpon/bbf-xpon-pm:activation" {
    deviate not-supported;
  }

// Deviations for bbf-xpon-pm:tuning control

  deviation "/if:interfaces-state/if:interface/bbf-if-pm:performance/bbf-if-pm:intervals-15min/bbf-if-pm:current/bbf-xpon-pm:xpon/bbf-xpon-pm:tuning-control" {
    deviate not-supported;
  }

// Deviations for bbf-xpon-pm:power-levelling

  deviation "/if:interfaces-state/if:interface/bbf-if-pm:performance/bbf-if-pm:intervals-15min/bbf-if-pm:current/bbf-xpon-pm:xpon/bbf-xpon-pm:power-levelling" {
    deviate not-supported;
  }

// Deviations for bbf-xpon-pm:omci

  deviation "/if:interfaces-state/if:interface/bbf-if-pm:performance/bbf-if-pm:intervals-15min/bbf-if-pm:current/bbf-xpon-pm:xpon/bbf-xpon-pm:omci" {
    deviate not-supported;
  }

// Deviations for bbf-xpon-pm:power-monitoring

  deviation "/if:interfaces-state/if:interface/bbf-if-pm:performance/bbf-if-pm:intervals-15min/bbf-if-pm:current/bbf-xpon-pm:xpon/bbf-xpon-pm:power-monitoring" {
    deviate not-supported;
  }

// Deviations for bbf-xpon-pm:energy-conservation

  deviation "/if:interfaces-state/if:interface/bbf-if-pm:performance/bbf-if-pm:intervals-15min/bbf-if-pm:current/bbf-xpon-pm:xpon/bbf-xpon-pm:energy-conservation" {
    deviate not-supported;
  }

// Deviations for history bbf-xpon-pm:phy

  deviation "/if:interfaces-state/if:interface/bbf-if-pm:performance/bbf-if-pm:intervals-15min/bbf-if-pm:history/bbf-xpon-pm:xpon/bbf-xpon-pm:phy/bbf-xpon-pm:psbd-hec-errors" {
    deviate not-supported;
  }

  deviation "/if:interfaces-state/if:interface/bbf-if-pm:performance/bbf-if-pm:intervals-15min/bbf-if-pm:history/bbf-xpon-pm:xpon/bbf-xpon-pm:phy/bbf-xpon-pm:fs-hec-errors" {
    deviate not-supported;
  }

  deviation "/if:interfaces-state/if:interface/bbf-if-pm:performance/bbf-if-pm:intervals-15min/bbf-if-pm:history/bbf-xpon-pm:xpon/bbf-xpon-pm:phy/bbf-xpon-pm:unknown-profiles" {
    deviate not-supported;
  }

  deviation "/if:interfaces-state/if:interface/bbf-if-pm:performance/bbf-if-pm:intervals-15min/bbf-if-pm:history/bbf-xpon-pm:xpon/bbf-xpon-pm:phy/bbf-xpon-pm:fec-seconds" {
    deviate not-supported;
  }

// Deviations for history bbf-xpon-pm:lods

  deviation "/if:interfaces-state/if:interface/bbf-if-pm:performance/bbf-if-pm:intervals-15min/bbf-if-pm:history/bbf-xpon-pm:xpon/bbf-xpon-pm:lods" {
    deviate not-supported;
  }

// Deviations for history bbf-xpon-pm:gemport

  deviation "/if:interfaces-state/if:interface/bbf-if-pm:performance/bbf-if-pm:intervals-15min/bbf-if-pm:history/bbf-xpon-pm:xpon/bbf-xpon-pm:gemport" {
    deviate not-supported;
  }

// Deviations for history bbf-xpon-pm:utilization

  deviation "/if:interfaces-state/if:interface/bbf-if-pm:performance/bbf-if-pm:intervals-15min/bbf-if-pm:history/bbf-xpon-pm:xpon/bbf-xpon-pm:utilization" {
    deviate not-supported;
  }

// Deviations for history bbf-xpon-pm:activation


  deviation "/if:interfaces-state/if:interface/bbf-if-pm:performance/bbf-if-pm:intervals-15min/bbf-if-pm:history/bbf-xpon-pm:xpon/bbf-xpon-pm:activation" {
    deviate not-supported;
  }

// Deviations for history bbf-xpon-pm:tuning-control

  deviation "/if:interfaces-state/if:interface/bbf-if-pm:performance/bbf-if-pm:intervals-15min/bbf-if-pm:history/bbf-xpon-pm:xpon/bbf-xpon-pm:tuning-control" {
    deviate not-supported;
  }

// Deviations for history bbf-xpon-pm:power-levelling

  deviation "/if:interfaces-state/if:interface/bbf-if-pm:performance/bbf-if-pm:intervals-15min/bbf-if-pm:history/bbf-xpon-pm:xpon/bbf-xpon-pm:power-levelling" {
    deviate not-supported;
  }

// Deviations for history bbf-xpon-pm:omci

  deviation "/if:interfaces-state/if:interface/bbf-if-pm:performance/bbf-if-pm:intervals-15min/bbf-if-pm:history/bbf-xpon-pm:xpon/bbf-xpon-pm:omci" {
    deviate not-supported;
  }

// Deviations for history bbf-xpon-pm:power-monitoring

  deviation "/if:interfaces-state/if:interface/bbf-if-pm:performance/bbf-if-pm:intervals-15min/bbf-if-pm:history/bbf-xpon-pm:xpon/bbf-xpon-pm:power-monitoring" {
    deviate not-supported;
  }

// Deviations for history bbf-xpon-pm:energy-conservation

  deviation "/if:interfaces-state/if:interface/bbf-if-pm:performance/bbf-if-pm:intervals-15min/bbf-if-pm:history/bbf-xpon-pm:xpon/bbf-xpon-pm:energy-conservation" {
    deviate not-supported;
  }


}
