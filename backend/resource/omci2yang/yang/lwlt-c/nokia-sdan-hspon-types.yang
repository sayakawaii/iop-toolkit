module nokia-sdan-hspon-types{

yang-version 1.1;

namespace "urn:broadband-forum-org:yang:nokia-sdan-hspon-types";
 
prefix nokia-sdan-hspon-types;

import bbf-xpon-types {
    prefix bbf-xpon-types;
}

organization
  "Nokia";

contact
  "Comments or questions about this Nokia YANG module should be
  directed to <mailto:isam.yang@nokia.com>.";

description
  "This specification is published by Nokia under Non-Disclosure
  Agreement(s) (NDA) with specific parties and has to be considered
  as Confidential Information as defined in such NDA. Nokia reserves
  the right to revise this document for any reason, including but
  not limited to conformity with standards promulgated by various
  agencies, utilization of advances in the state of the technical
  areas, or the reflection of changes in the design of any
  equipment, techniques, or procedures described or referred to
  herein.

  The product specifications and other technical or performance
  information contained herein are subject to change without notice.
  Updates of this document will be issued under the above NDA's.

  Nokia makes no representation or warranty, expressed or implied,
  with respect to the sufficiency, accuracy, or utility of any
  information or opinion contained herein. Nokia expressly advises
  that any use of for any purpose or reliance upon this technical
  reference is at the risk of the user and that Nokia shall not be
  liable for any damage or injury incurred by any person arising out
  of the sufficiency, accuracy, or utility of any information or
  opinion contained herein.

  This document is not to be construed as a suggestion to any
  manufacturer to modify or change any of its products, nor does
  this document represent any commitment by Nokia to sell or
  purchase any product. Nothing contained herein shall be construed
  as conferring by implication, estoppel, or otherwise any license
  or right under any patent, whether or not the use of any
  information herein necessarily employs an invention of any
  existing or later issued patent.

  Nokia reserves the right not to offer any or all of these products
  and to withdraw any or all of them at any future time.

  Copyright (C) 2022, Nokia. All Rights Reserved";

revision 2024-05-09 {
  description
    "add flex FEC for 50G pon only.";
  reference
    "TBD";
}

revision 2022-04-19 {
  description
    "Initial revision.";
  reference
    "TBD";
}

identity hs-pon {
    base bbf-xpon-types:channel-pair-type-base;
    description
      "This identity is used to denote a HS-PON channel-pair,
       per ITU-T <TBD>.";
  }

identity fec-type-base {
    description
      "This identity is used to define different types of FEC.";
  }

identity fec-type-system-selected {
    base nokia-sdan-hspon-types:fec-type-base;
    description
      "This identity is used to specify that the system can select the FEC type
       that by default fits with the technology.";
  }

identity fec-type-ldpc {
    base nokia-sdan-hspon-types:fec-type-base;
    description
      "This identity is used to specify Low Density Parity Check FEC to be used.";
  }

identity fec-type-rs {
    base nokia-sdan-hspon-types:fec-type-base;
    description
      "This identity is used to specify Reed Solomon FEC to be used.";
  }


identity hs-pon-channel-pair-line-rate-profile-base {
  description
    "This identity is used to define the possible combinations
     of downstream and upstream line-rates for a HS-PON
     channel-pair.";
  }

identity unplanned-hs-pon-cp-line-rate {
  base nokia-sdan-hspon-types:hs-pon-channel-pair-line-rate-profile-base;
  description
    "This identity is used to denote a HS-PON channel pair with
     yet undefined downstream and upstream line rates.";
  }

identity down-50-up-25 {
  base nokia-sdan-hspon-types:hs-pon-channel-pair-line-rate-profile-base;
  description
    "This identity is used to denote a HS-PON channel pair with
     downstream 50Gbps and upstream 25Gbps|12,5Gbps dual-rate line rates.";
  }

identity down-25-up-25 {
  base nokia-sdan-hspon-types:hs-pon-channel-pair-line-rate-profile-base;
  description
    "This identity is used to denote a HS-PON channel pair with
     downstream 25Gbps and upstream 25Gbps|12,5Gbps dual-rate line rates.";
  }

  identity fec-type-ldpc-high-margin {
    base nokia-sdan-hspon-types:fec-type-base;
    description
      "This identity is used to specify High Margin LDPC FEC to be used.";
  }
}
