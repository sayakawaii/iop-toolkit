submodule bbf-pots-interworking-frommounted {
  yang-version 1.1;
  belongs-to bbf-sip-voip-frommounted  {
    prefix bbf-sip-voip-frommounted;
  }
  
  
  import bbf-yang-types {
    prefix bbf-yang;
  }
  

  import bbf-fiber-onu-emulated-mount {
     prefix onu;
  }



  
  
  
  include bbf-sip-voip-base-frommounted;
  include bbf-sip-terminations-frommounted;
  include bbf-voip-access-gateways-frommounted;

  
  organization
    "Broadband Forum <https://www.broadband-forum.org>
     Common YANG Work Area";

  contact
    "Comments or questions about this Broadband Forum YANG module
     should be directed to <mailto:help@broadband-forum.org>.
     Editor:      Joey Boyd, ADTRAN
     Editor:      Ludwig Pauwels, Nokia
     PS Leader:   Joey Boyd, ADTRAN
     PS Leader:   Ken Kerpez, ASSIA
     WA Director: Joey Boyd, ADTRAN
     WA Director: Sven Ooghe, Nokia";

  description
    "This submodule contains a collection of YANG definitions for
     managing the pots interworking function.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2021-09-27 {
    description
      "Add a reference to an onu-v-vrefpoint interface in
       pots-interworking. Add when statements for sip-user-name,
       voip-access-gateway and voip-vrefpoint-interface.";
    reference
      "";
  }
  revision 2021-07-06 {
    description
      "Add session-type in pots-x-connections container";
    reference
      "";
  } 
  revision 2021-03-24 {
    description
      "Initial revision.
       * Approval Date:    see revision date above.
       * Publication Date: 2020-03-06.";
    reference
      " ";
  }
  
 augment '/onu:onus/onu:onu/onu:fromroot' {
  container pots-interworking-nodes {
    presence "pots-interworking-nodes";
    description 
	  "The pots interworking function.";
    list pots-interworking {
	  key "name";
	  description
        "Pots interworking nodes.";
      leaf name {
        type bbf-yang:name-string;    
	    description
     	  "Uniquely identifies the POTS interworking node.";
      }
	  leaf phys-pots-itf {
           type string;
   	      description
   	         "References a physical Voice interface.";
      }
	  leaf sip-user-name {
        /* type bbf-sip-voip-frommounted:sip-termination-ref; */
          type string;
        description
	      "References the SIP user name.";
      }
	  leaf voip-access-gateway {
        /* type bbf-sip-voip-frommounted:voip-access-gateway-ref;*/
     type string;
	    description
	      "Uniquely identifies the Sip user agent on the 
	  	   network SIP interface side.";
	  }
    }
  }
}
  
}
