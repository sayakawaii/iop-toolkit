submodule bbf-sip-user-agent-frommounted {
  yang-version 1.1;
  belongs-to bbf-sip-voip-frommounted  {
    prefix bbf-sip-voip-frommounted;
  }
  
  import bbf-yang-types {
    prefix bbf-yang;
  }

  import bbf-fiber-onu-emulated-mount {
     prefix onu;
  }
  

  include bbf-sip-types-frommounted;
  include bbf-sip-transport-protocol-characteristics-frommounted;
  include bbf-voip-service-gateway-frommounted;
  include bbf-sip-voip-base-frommounted;
  
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains a collection of YANG definitions for
     managing Sip User Agent  configuration profile.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2021-03-24 {
    description
      "Initial revision.
       * Approval Date:    see revision date above.
       * Publication Date: 2020-03-06.";
    reference
      " ";
  }
  
  /* typedef sip-user-agent {
    type string;
    description
      "References a sip user agent.";
  } */
  
  augment "/onu:onus/onu:onu/onu:fromroot/bbf-sip-voip-frommounted:sip-signaling"
        + "/bbf-sip-voip-frommounted:sip-user-agents" {
    list sip-user-agent {
      key name;
	  leaf name {
	    type bbf-yang:string-ascii64;
	    description
	      "The name of the SIP User Agent instance.";
	}    	
/*	moved towards the IP interface, DHCP and vlan subitf
    are decided on IP itf, vsi via Nokia-ip-aug.yang
    leaf sip-config-mode {
	  type enumeration {
	    enum manual {
		  value 1;
		}
		enum dhcpv4 {
		  value 2;
		}			  
	  }
	  description
          "The way the SIP user agent gets provisioned.";
	}  */	
	leaf voip-service-gateway {
      /*    type voip-service-gateway-ref; */
   type string;
	  description
	    "References a Voip Service Gateway (VAG).";
	}
	leaf sip-user-agent-domain {
      type string
      {
        length "0..100";
      }
	  description
	    "The SIP User Agent domain. This will be the host part of 
		 the sip-uri of all sip terminations belonging to this sip 
		 user agent";
	}  
    leaf sip-uni-uri-type {
      type enumeration {
        enum sip-uri {
          value 1;
          description
            "SIP Uniform Resource Identifier.";
        }
        enum tel-uri {
          value 2;
          description
            "TEL Uniform Resource Identifier.";
        }
      }
      description
        "The SIP uni URI type.";
    }
    }
  }

}
